-- ASN1START
-- **************************************************************
--
-- Elementary Procedure definitions
--
-- **************************************************************

F1AP-PDU-Descriptions {
   itu-t (0) identified-organization (4) etsi (0) mobileDomain (0)
ngran-access (22) modules (3) f1ap (3) version1 (1) f1ap-PDU-Descriptions (0)}

DEFINITIONS AUTOMATIC TAGS ::=

BEGIN

-- **************************************************************
--
-- IE parameter types from other modules.
--
-- **************************************************************

IMPORTS
Criticality,
ProcedureCode

FROM F1AP-CommonDataTypes
Reset,
ResetAcknowledge,
F1SetupRequest,
F1SetupResponse,
F1SetupFailure,
GNBDUConfigurationUpdate,
GNBDUConfigurationUpdateAcknowledge,
GNBDUConfigurationUpdateFailure,
GNBCUConfigurationUpdate,
GNBCUConfigurationUpdateAcknowledge,
GNBCUConfigurationUpdateFailure,
UEContextSetupRequest,
UEContextSetupResponse,
UEContextSetupFailure,
UEContextReleaseCommand,
UEContextReleaseComplete,
UEContextModificationRequest,
UEContextModificationResponse,
UEContextModificationFailure,
UEContextModificationRequired,
UEContextModificationConfirm,
ErrorIndication,
UEContextReleaseRequest,
DLRRCMessageTransfer,
ULRRCMessageTransfer,
GNBDUResourceCoordinationRequest,
GNBDUResourceCoordinationResponse,
PrivateMessage,
UEInactivityNotification,
InitialULRRCMessageTransfer,
SystemInformationDeliveryCommand,
Paging,
Notify,
WriteReplaceWarningRequest,
WriteReplaceWarningResponse,
PWSCancelRequest,
PWSCancelResponse,
PWSRestartIndication,
PWSFailureIndication,
GNBDUStatusIndication,
RRCDeliveryReport,
UEContextModificationRefuse,
F1RemovalRequest,
F1RemovalResponse,
F1RemovalFailure,
NetworkAccessRateReduction,
TraceStart,
DeactivateTrace,
DUCURadioInformationTransfer,
CUDURadioInformationTransfer,
BAPMappingConfiguration,
BAPMappingConfigurationAcknowledge,
BAPMappingConfigurationFailure,
GNBDUResourceConfiguration,
GNBDUResourceConfigurationAcknowledge,
GNBDUResourceConfigurationFailure,
IABTNLAddressRequest,
IABTNLAddressResponse,
IABTNLAddressFailure,
IABUPConfigurationUpdateRequest,
IABUPConfigurationUpdateResponse,
IABUPConfigurationUpdateFailure,
ResourceStatusRequest,
ResourceStatusResponse,
ResourceStatusFailure,
ResourceStatusUpdate,
AccessAndMobilityIndication,
ReferenceTimeInformationReportingControl,
ReferenceTimeInformationReport,
AccessSuccess,
CellTrafficTrace,
PositioningMeasurementRequest,
PositioningMeasurementResponse,
PositioningMeasurementFailure,
PositioningAssistanceInformationControl,
PositioningAssistanceInformationFeedback,
PositioningMeasurementReport,
PositioningMeasurementAbort,
PositioningMeasurementFailureIndication,
PositioningMeasurementUpdate,
TRPInformationRequest,
TRPInformationResponse,
TRPInformationFailure,
PositioningInformationRequest,
PositioningInformationResponse,
PositioningInformationFailure,
PositioningActivationRequest,
PositioningActivationResponse,
PositioningActivationFailure,
PositioningDeactivation,
PositioningInformationUpdate,
E-CIDMeasurementInitiationRequest,
E-CIDMeasurementInitiationResponse,
E-CIDMeasurementInitiationFailure,
E-CIDMeasurementFailureIndication,
E-CIDMeasurementReport,
E-CIDMeasurementTerminationCommand

FROM F1AP-PDU-Contents
id-Reset,
id-F1Setup,
id-gNBDUConfigurationUpdate,
id-gNBCUConfigurationUpdate,
id-UEContextSetup,
id-UEContextRelease,
id-UEContextModification,
id-UEContextModificationRequired,
id-ErrorIndication,
id-UEContextReleaseRequest,
id-DLRRCMessageTransfer,
id-ULRRCMessageTransfer,
id-GNBDUResourceCoordination,
id-privateMessage,
id-UEInactivityNotification,
id-InitialULRRCMessageTransfer,
id-SystemInformationDeliveryCommand,
id-Paging,
id-Notify,
id-WriteReplaceWarning,
id-PWSCancel,
id-PWSRestartIndication,
id-PWSFailureIndication,
id-GNBDUStatusIndication,
id-RRCDeliveryReport,
id-F1Removal,
id-NetworkAccessRateReduction,
id-TraceStart,
id-DeactivateTrace,
id-DUCURadioInformationTransfer,
id-CUDURadioInformationTransfer,
id-BAPMappingConfiguration,
id-GNBDUResourceConfiguration,
id-IABTNLAddressAllocation,
id-IABUPConfigurationUpdate,
id-resourceStatusReportingInitiation,
id-resourceStatusReporting,
id-accessAndMobilityIndication,
id-ReferenceTimeInformationReportingControl,
id-ReferenceTimeInformationReport,
id-accessSuccess,
id-cellTrafficTrace,
id-PositioningMeasurementExchange,
id-PositioningAssistanceInformationControl,
id-PositioningAssistanceInformationFeedback,
id-PositioningMeasurementReport,
id-PositioningMeasurementAbort,
id-PositioningMeasurementFailureIndication,
id-PositioningMeasurementUpdate,
id-TRPInformationExchange,
id-PositioningInformationExchange,
id-PositioningActivation,
id-PositioningDeactivation,
id-PositioningInformationUpdate,
id-E-CIDMeasurementInitiation,
id-E-CIDMeasurementFailureIndication,
id-E-CIDMeasurementReport,
id-E-CIDMeasurementTermination

FROM F1AP-Constants

ProtocolIE-SingleContainer{},
F1AP-PROTOCOL-IES

FROM F1AP-Containers;

-- **************************************************************
--
-- Interface Elementary Procedure Class
--
-- **************************************************************

F1AP-ELEMENTARY-PROCEDURE ::= CLASS {
   &InitiatingMessage ,
   &SuccessfulOutcome OPTIONAL,
   &UnsuccessfulOutcome OPTIONAL,
   &procedureCode ProcedureCode UNIQUE,
   &criticality Criticality DEFAULT ignore
}
WITH SYNTAX {
   INITIATING MESSAGE &InitiatingMessage
   [SUCCESSFUL OUTCOME &SuccessfulOutcome]
   [UNSUCCESSFUL OUTCOME &UnsuccessfulOutcome]
   PROCEDURE CODE &procedureCode
   [CRITICALITY &criticality]
}

-- **************************************************************
--
-- Interface PDU Definition
--
-- **************************************************************

F1AP-PDU ::= CHOICE {
   initiatingMessage InitiatingMessage,
   successfulOutcome SuccessfulOutcome,
   unsuccessfulOutcome UnsuccessfulOutcome,
   choice-extension ProtocolIE-SingleContainer { { F1AP-PDU-ExtIEs} }
}

F1AP-PDU-ExtIEs F1AP-PROTOCOL-IES ::= { -- this extension is not used
   ...
}

InitiatingMessage ::= SEQUENCE {
   procedureCode F1AP-ELEMENTARY-PROCEDURE.&procedureCode ({F1AP-ELEMENTARY-PROCEDURES}),
   criticality F1AP-ELEMENTARY-PROCEDURE.&criticality ({F1AP-ELEMENTARY-PROCEDURES}{@procedureCode}),
   value F1AP-ELEMENTARY-PROCEDURE.&InitiatingMessage ({F1AP-ELEMENTARY-PROCEDURES}{@procedureCode})
}

SuccessfulOutcome ::= SEQUENCE {
   procedureCode F1AP-ELEMENTARY-PROCEDURE.&procedureCode ({F1AP-ELEMENTARY-PROCEDURES}),
   criticality F1AP-ELEMENTARY-PROCEDURE.&criticality ({F1AP-ELEMENTARY-PROCEDURES}{@procedureCode}),
   value F1AP-ELEMENTARY-PROCEDURE.&SuccessfulOutcome ({F1AP-ELEMENTARY-PROCEDURES}{@procedureCode})
}

UnsuccessfulOutcome ::= SEQUENCE {
   procedureCode F1AP-ELEMENTARY-PROCEDURE.&procedureCode ({F1AP-ELEMENTARY-PROCEDURES}),
   criticality F1AP-ELEMENTARY-PROCEDURE.&criticality ({F1AP-ELEMENTARY-PROCEDURES}{@procedureCode}),
   value F1AP-ELEMENTARY-PROCEDURE.&UnsuccessfulOutcome ({F1AP-ELEMENTARY-PROCEDURES}{@procedureCode})
}

-- **************************************************************
--
-- Interface Elementary Procedure List
--
-- **************************************************************

F1AP-ELEMENTARY-PROCEDURES F1AP-ELEMENTARY-PROCEDURE ::= {
   F1AP-ELEMENTARY-PROCEDURES-CLASS-1 |
   F1AP-ELEMENTARY-PROCEDURES-CLASS-2,
   ...
}

F1AP-ELEMENTARY-PROCEDURES-CLASS-1 F1AP-ELEMENTARY-PROCEDURE ::= {
   reset |
   f1Setup |
   gNBDUConfigurationUpdate |
   gNBCUConfigurationUpdate |
   uEContextSetup |
   uEContextRelease |
   uEContextModification |
   uEContextModificationRequired |
   writeReplaceWarning |
   pWSCancel |
   gNBDUResourceCoordination |
   f1Removal |
   bAPMappingConfiguration |
   gNBDUResourceConfiguration |
   iABTNLAddressAllocation |
   iABUPConfigurationUpdate |
   resourceStatusReportingInitiation |
   positioningMeasurementExchange |
   tRPInformationExchange |
   positioningInformationExchange |
   positioningActivation |
   e-CIDMeasurementInitiation,
   ...
}

F1AP-ELEMENTARY-PROCEDURES-CLASS-2 F1AP-ELEMENTARY-PROCEDURE ::= {
   errorIndication |
   uEContextReleaseRequest |
   dLRRCMessageTransfer |
   uLRRCMessageTransfer |
   uEInactivityNotification |
   privateMessage |
   initialULRRCMessageTransfer |
   systemInformationDelivery |
   paging |
   notify |
   pWSRestartIndication |
   pWSFailureIndication |
   gNBDUStatusIndication |
   rRCDeliveryReport |
   networkAccessRateReduction |
   traceStart |
   deactivateTrace |
   dUCURadioInformationTransfer |
   cUDURadioInformationTransfer |
   resourceStatusReporting |
   accessAndMobilityIndication |
   referenceTimeInformationReportingControl|
   referenceTimeInformationReport |
   accessSuccess |
   cellTrafficTrace |
   positioningAssistanceInformationControl |
   positioningAssistanceInformationFeedback |
   positioningMeasurementReport |
   positioningMeasurementAbort |
   positioningMeasurementFailureIndication |
   positioningMeasurementUpdate |
   positioningDeactivation |
   e-CIDMeasurementFailureIndication |
   e-CIDMeasurementReport |
   e-CIDMeasurementTermination |
   positioningInformationUpdate,
   ...
}
-- **************************************************************
--
-- Interface Elementary Procedures
--
-- **************************************************************

reset F1AP-ELEMENTARY-PROCEDURE ::= {
   INITIATING MESSAGE Reset
   SUCCESSFUL OUTCOME ResetAcknowledge
   PROCEDURE CODE id-Reset
   CRITICALITY reject
}

f1Setup F1AP-ELEMENTARY-PROCEDURE ::= {
   INITIATING MESSAGE F1SetupRequest
   SUCCESSFUL OUTCOME F1SetupResponse
   UNSUCCESSFUL OUTCOME F1SetupFailure
   PROCEDURE CODE id-F1Setup
   CRITICALITY reject
}

gNBDUConfigurationUpdate F1AP-ELEMENTARY-PROCEDURE ::= {
   INITIATING MESSAGE GNBDUConfigurationUpdate
   SUCCESSFUL OUTCOME GNBDUConfigurationUpdateAcknowledge
   UNSUCCESSFUL OUTCOME GNBDUConfigurationUpdateFailure
   PROCEDURE CODE id-gNBDUConfigurationUpdate
   CRITICALITY reject
}

gNBCUConfigurationUpdate F1AP-ELEMENTARY-PROCEDURE ::= {
   INITIATING MESSAGE GNBCUConfigurationUpdate
   SUCCESSFUL OUTCOME GNBCUConfigurationUpdateAcknowledge
   UNSUCCESSFUL OUTCOME GNBCUConfigurationUpdateFailure
   PROCEDURE CODE id-gNBCUConfigurationUpdate
   CRITICALITY reject
}

uEContextSetup F1AP-ELEMENTARY-PROCEDURE ::= {
   INITIATING MESSAGE UEContextSetupRequest
   SUCCESSFUL OUTCOME UEContextSetupResponse
   UNSUCCESSFUL OUTCOME UEContextSetupFailure
   PROCEDURE CODE id-UEContextSetup
   CRITICALITY reject
}

uEContextRelease F1AP-ELEMENTARY-PROCEDURE ::= {
   INITIATING MESSAGE UEContextReleaseCommand
   SUCCESSFUL OUTCOME UEContextReleaseComplete
   PROCEDURE CODE id-UEContextRelease
   CRITICALITY reject
}

uEContextModification F1AP-ELEMENTARY-PROCEDURE ::= {
   INITIATING MESSAGE UEContextModificationRequest
   SUCCESSFUL OUTCOME UEContextModificationResponse
   UNSUCCESSFUL OUTCOME UEContextModificationFailure
   PROCEDURE CODE id-UEContextModification
   CRITICALITY reject
}

uEContextModificationRequired F1AP-ELEMENTARY-PROCEDURE ::= {
   INITIATING MESSAGE UEContextModificationRequired
   SUCCESSFUL OUTCOME UEContextModificationConfirm
   UNSUCCESSFUL OUTCOME UEContextModificationRefuse
   PROCEDURE CODE id-UEContextModificationRequired
   CRITICALITY reject
}

writeReplaceWarning F1AP-ELEMENTARY-PROCEDURE ::= {
   INITIATING MESSAGE WriteReplaceWarningRequest
   SUCCESSFUL OUTCOME WriteReplaceWarningResponse
   PROCEDURE CODE id-WriteReplaceWarning
   CRITICALITY reject
}

pWSCancel F1AP-ELEMENTARY-PROCEDURE ::= {
   INITIATING MESSAGE PWSCancelRequest
   SUCCESSFUL OUTCOME PWSCancelResponse
   PROCEDURE CODE id-PWSCancel
   CRITICALITY reject
}

errorIndication F1AP-ELEMENTARY-PROCEDURE ::= {
   INITIATING MESSAGE ErrorIndication
   PROCEDURE CODE id-ErrorIndication
   CRITICALITY ignore
}

uEContextReleaseRequest F1AP-ELEMENTARY-PROCEDURE ::= {
   INITIATING MESSAGE UEContextReleaseRequest
   PROCEDURE CODE id-UEContextReleaseRequest
   CRITICALITY ignore
}

initialULRRCMessageTransfer F1AP-ELEMENTARY-PROCEDURE ::= {
   INITIATING MESSAGE InitialULRRCMessageTransfer
   PROCEDURE CODE id-InitialULRRCMessageTransfer
   CRITICALITY ignore
}

dLRRCMessageTransfer F1AP-ELEMENTARY-PROCEDURE ::= {
   INITIATING MESSAGE DLRRCMessageTransfer
   PROCEDURE CODE id-DLRRCMessageTransfer
   CRITICALITY ignore
}

uLRRCMessageTransfer F1AP-ELEMENTARY-PROCEDURE ::= {
   INITIATING MESSAGE ULRRCMessageTransfer
   PROCEDURE CODE id-ULRRCMessageTransfer
   CRITICALITY ignore
}

uEInactivityNotification F1AP-ELEMENTARY-PROCEDURE ::= {
   INITIATING MESSAGE UEInactivityNotification
   PROCEDURE CODE id-UEInactivityNotification
   CRITICALITY ignore
}

gNBDUResourceCoordination F1AP-ELEMENTARY-PROCEDURE ::= {
   INITIATING MESSAGE GNBDUResourceCoordinationRequest
   SUCCESSFUL OUTCOME GNBDUResourceCoordinationResponse
   PROCEDURE CODE id-GNBDUResourceCoordination
   CRITICALITY reject
}

privateMessage F1AP-ELEMENTARY-PROCEDURE ::= {
   INITIATING MESSAGE PrivateMessage
   PROCEDURE CODE id-privateMessage
   CRITICALITY ignore
}

systemInformationDelivery F1AP-ELEMENTARY-PROCEDURE ::= {
   INITIATING MESSAGE SystemInformationDeliveryCommand
   PROCEDURE CODE id-SystemInformationDeliveryCommand
   CRITICALITY ignore
}

paging F1AP-ELEMENTARY-PROCEDURE ::= {
   INITIATING MESSAGE Paging
   PROCEDURE CODE id-Paging
   CRITICALITY ignore
}

notify F1AP-ELEMENTARY-PROCEDURE ::= {
   INITIATING MESSAGE Notify
   PROCEDURE CODE id-Notify
   CRITICALITY ignore
}

networkAccessRateReduction F1AP-ELEMENTARY-PROCEDURE ::= {
   INITIATING MESSAGE NetworkAccessRateReduction
   PROCEDURE CODE id-NetworkAccessRateReduction
   CRITICALITY ignore
}

pWSRestartIndication F1AP-ELEMENTARY-PROCEDURE ::= {
   INITIATING MESSAGE PWSRestartIndication
   PROCEDURE CODE id-PWSRestartIndication
   CRITICALITY ignore
}

pWSFailureIndication F1AP-ELEMENTARY-PROCEDURE ::= {
   INITIATING MESSAGE PWSFailureIndication
   PROCEDURE CODE id-PWSFailureIndication
   CRITICALITY ignore
}

gNBDUStatusIndication F1AP-ELEMENTARY-PROCEDURE ::= {
   INITIATING MESSAGE GNBDUStatusIndication
   PROCEDURE CODE id-GNBDUStatusIndication
   CRITICALITY ignore
}

rRCDeliveryReport F1AP-ELEMENTARY-PROCEDURE ::= {
   INITIATING MESSAGE RRCDeliveryReport
   PROCEDURE CODE id-RRCDeliveryReport
   CRITICALITY ignore
}

f1Removal F1AP-ELEMENTARY-PROCEDURE ::= {
   INITIATING MESSAGE F1RemovalRequest
   SUCCESSFUL OUTCOME F1RemovalResponse
   UNSUCCESSFUL OUTCOME F1RemovalFailure
   PROCEDURE CODE id-F1Removal
   CRITICALITY reject
}

traceStart F1AP-ELEMENTARY-PROCEDURE ::= {
   INITIATING MESSAGE TraceStart
   PROCEDURE CODE id-TraceStart
   CRITICALITY ignore
}

deactivateTrace F1AP-ELEMENTARY-PROCEDURE ::= {
   INITIATING MESSAGE DeactivateTrace
   PROCEDURE CODE id-DeactivateTrace
   CRITICALITY ignore
}

dUCURadioInformationTransfer F1AP-ELEMENTARY-PROCEDURE ::= {
   INITIATING MESSAGE DUCURadioInformationTransfer
   PROCEDURE CODE id-DUCURadioInformationTransfer
   CRITICALITY ignore
}

cUDURadioInformationTransfer F1AP-ELEMENTARY-PROCEDURE ::= {
   INITIATING MESSAGE CUDURadioInformationTransfer
   PROCEDURE CODE id-CUDURadioInformationTransfer
   CRITICALITY ignore
}

bAPMappingConfiguration F1AP-ELEMENTARY-PROCEDURE ::= {
   INITIATING MESSAGE BAPMappingConfiguration
   SUCCESSFUL OUTCOME BAPMappingConfigurationAcknowledge
   UNSUCCESSFUL OUTCOME BAPMappingConfigurationFailure
   PROCEDURE CODE id-BAPMappingConfiguration
   CRITICALITY reject
}

gNBDUResourceConfiguration F1AP-ELEMENTARY-PROCEDURE ::= {
   INITIATING MESSAGE GNBDUResourceConfiguration
   SUCCESSFUL OUTCOME GNBDUResourceConfigurationAcknowledge
   UNSUCCESSFUL OUTCOME GNBDUResourceConfigurationFailure
   PROCEDURE CODE id-GNBDUResourceConfiguration
   CRITICALITY reject
}

iABTNLAddressAllocation F1AP-ELEMENTARY-PROCEDURE ::= {
   INITIATING MESSAGE IABTNLAddressRequest
   SUCCESSFUL OUTCOME IABTNLAddressResponse
   UNSUCCESSFUL OUTCOME IABTNLAddressFailure
   PROCEDURE CODE id-IABTNLAddressAllocation
   CRITICALITY reject
}

iABUPConfigurationUpdate F1AP-ELEMENTARY-PROCEDURE ::= {
   INITIATING MESSAGE IABUPConfigurationUpdateRequest
   SUCCESSFUL OUTCOME IABUPConfigurationUpdateResponse
   UNSUCCESSFUL OUTCOME IABUPConfigurationUpdateFailure
   PROCEDURE CODE id-IABUPConfigurationUpdate
   CRITICALITY reject
}

resourceStatusReportingInitiation F1AP-ELEMENTARY-PROCEDURE ::= {
   INITIATING MESSAGE ResourceStatusRequest
   SUCCESSFUL OUTCOME ResourceStatusResponse
   UNSUCCESSFUL OUTCOME ResourceStatusFailure
   PROCEDURE CODE id-resourceStatusReportingInitiation
   CRITICALITY reject
}

resourceStatusReporting F1AP-ELEMENTARY-PROCEDURE ::= {
   INITIATING MESSAGE ResourceStatusUpdate
   PROCEDURE CODE id-resourceStatusReporting
   CRITICALITY ignore
}

accessAndMobilityIndication F1AP-ELEMENTARY-PROCEDURE ::= {
   INITIATING MESSAGE AccessAndMobilityIndication
   PROCEDURE CODE id-accessAndMobilityIndication
   CRITICALITY ignore
}

referenceTimeInformationReportingControl F1AP-ELEMENTARY-PROCEDURE ::= {
   INITIATING MESSAGE ReferenceTimeInformationReportingControl
   PROCEDURE CODE id-ReferenceTimeInformationReportingControl
   CRITICALITY ignore
}

referenceTimeInformationReport F1AP-ELEMENTARY-PROCEDURE ::= {
   INITIATING MESSAGE ReferenceTimeInformationReport
   PROCEDURE CODE id-ReferenceTimeInformationReport
   CRITICALITY ignore
}

accessSuccess F1AP-ELEMENTARY-PROCEDURE ::= {
   INITIATING MESSAGE AccessSuccess
   PROCEDURE CODE id-accessSuccess
   CRITICALITY ignore
}

cellTrafficTrace F1AP-ELEMENTARY-PROCEDURE ::= {
   INITIATING MESSAGE CellTrafficTrace
   PROCEDURE CODE id-cellTrafficTrace
   CRITICALITY ignore
}

positioningAssistanceInformationControl F1AP-ELEMENTARY-PROCEDURE ::= {
   INITIATING MESSAGE PositioningAssistanceInformationControl
   PROCEDURE CODE id-PositioningAssistanceInformationControl
   CRITICALITY ignore
}

positioningAssistanceInformationFeedback F1AP-ELEMENTARY-PROCEDURE ::= {
   INITIATING MESSAGE PositioningAssistanceInformationFeedback
   PROCEDURE CODE id-PositioningAssistanceInformationFeedback
   CRITICALITY ignore
}

positioningMeasurementExchange F1AP-ELEMENTARY-PROCEDURE ::= {
   INITIATING MESSAGE PositioningMeasurementRequest
   SUCCESSFUL OUTCOME PositioningMeasurementResponse
   UNSUCCESSFUL OUTCOME PositioningMeasurementFailure
   PROCEDURE CODE id-PositioningMeasurementExchange
   CRITICALITY reject
}

positioningMeasurementReport F1AP-ELEMENTARY-PROCEDURE ::= {
   INITIATING MESSAGE PositioningMeasurementReport
   PROCEDURE CODE id-PositioningMeasurementReport
   CRITICALITY ignore
}

positioningMeasurementAbort F1AP-ELEMENTARY-PROCEDURE ::= {
   INITIATING MESSAGE PositioningMeasurementAbort
   PROCEDURE CODE id-PositioningMeasurementAbort
   CRITICALITY ignore
}

positioningMeasurementFailureIndication F1AP-ELEMENTARY-PROCEDURE ::= {
   INITIATING MESSAGE PositioningMeasurementFailureIndication
   PROCEDURE CODE id-PositioningMeasurementFailureIndication
   CRITICALITY ignore
}

positioningMeasurementUpdate F1AP-ELEMENTARY-PROCEDURE ::= {
   INITIATING MESSAGE PositioningMeasurementUpdate
   PROCEDURE CODE id-PositioningMeasurementUpdate
   CRITICALITY ignore
}

tRPInformationExchange F1AP-ELEMENTARY-PROCEDURE ::= {
   INITIATING MESSAGE TRPInformationRequest
   SUCCESSFUL OUTCOME TRPInformationResponse
   UNSUCCESSFUL OUTCOME TRPInformationFailure
   PROCEDURE CODE id-TRPInformationExchange
   CRITICALITY reject
}

positioningInformationExchange F1AP-ELEMENTARY-PROCEDURE ::= {
   INITIATING MESSAGE PositioningInformationRequest
   SUCCESSFUL OUTCOME PositioningInformationResponse
   UNSUCCESSFUL OUTCOME PositioningInformationFailure
   PROCEDURE CODE id-PositioningInformationExchange
   CRITICALITY reject
}

positioningActivation F1AP-ELEMENTARY-PROCEDURE ::= {
   INITIATING MESSAGE PositioningActivationRequest
   SUCCESSFUL OUTCOME PositioningActivationResponse
   UNSUCCESSFUL OUTCOME PositioningActivationFailure
   PROCEDURE CODE id-PositioningActivation
   CRITICALITY reject
}

positioningDeactivation F1AP-ELEMENTARY-PROCEDURE ::= {
   INITIATING MESSAGE PositioningDeactivation
   PROCEDURE CODE id-PositioningDeactivation
   CRITICALITY ignore
}

e-CIDMeasurementInitiation F1AP-ELEMENTARY-PROCEDURE ::= {
   INITIATING MESSAGE E-CIDMeasurementInitiationRequest
   SUCCESSFUL OUTCOME E-CIDMeasurementInitiationResponse
   UNSUCCESSFUL OUTCOME E-CIDMeasurementInitiationFailure
   PROCEDURE CODE id-E-CIDMeasurementInitiation
   CRITICALITY reject
}

e-CIDMeasurementFailureIndication F1AP-ELEMENTARY-PROCEDURE ::= {
   INITIATING MESSAGE E-CIDMeasurementFailureIndication
   PROCEDURE CODE id-E-CIDMeasurementFailureIndication
   CRITICALITY ignore
}

e-CIDMeasurementReport F1AP-ELEMENTARY-PROCEDURE ::= {
   INITIATING MESSAGE E-CIDMeasurementReport
   PROCEDURE CODE id-E-CIDMeasurementReport
   CRITICALITY ignore
}

e-CIDMeasurementTermination F1AP-ELEMENTARY-PROCEDURE ::= {
   INITIATING MESSAGE E-CIDMeasurementTerminationCommand
   PROCEDURE CODE id-E-CIDMeasurementTermination
   CRITICALITY ignore
}

positioningInformationUpdate F1AP-ELEMENTARY-PROCEDURE ::= {
   INITIATING MESSAGE PositioningInformationUpdate
   PROCEDURE CODE id-PositioningInformationUpdate
   CRITICALITY ignore
}

END
-- ASN1STOP

-- ASN1START
-- **************************************************************
--
-- PDU definitions for F1AP.
--
-- **************************************************************

F1AP-PDU-Contents {
   itu-t (0) identified-organization (4) etsi (0) mobileDomain (0)
ngran-access (22) modules (3) f1ap (3) version1 (1) f1ap-PDU-Contents (1) }

DEFINITIONS AUTOMATIC TAGS ::=

BEGIN

-- **************************************************************
--
-- IE parameter types from other modules.
--
-- **************************************************************

IMPORTS
Candidate-SpCell-Item,
Cause,
Cells-Failed-to-be-Activated-List-Item,
Cells-Status-Item,
Cells-to-be-Activated-List-Item,
Cells-to-be-Deactivated-List-Item,
CellULConfigured,
CriticalityDiagnostics,
C-RNTI,
CUtoDURRCInformation,
DRB-Activity-Item,
DRBID,
DRBs-FailedToBeModified-Item,
DRBs-FailedToBeSetup-Item,
DRBs-FailedToBeSetupMod-Item,
DRB-Notify-Item,
DRBs-ModifiedConf-Item,
DRBs-Modified-Item,
DRBs-Required-ToBeModified-Item,
DRBs-Required-ToBeReleased-Item,
DRBs-Setup-Item,
DRBs-SetupMod-Item,
DRBs-ToBeModified-Item,
DRBs-ToBeReleased-Item,
DRBs-ToBeSetup-Item,
DRBs-ToBeSetupMod-Item,
DRXCycle,
DRXConfigurationIndicator,
DUtoCURRCInformation,
EUTRANQoS,
ExecuteDuplication,
FullConfiguration,
GNB-CU-UE-F1AP-ID,
GNB-DU-UE-F1AP-ID,
GNB-DU-ID,
GNB-DU-Served-Cells-Item,
GNB-DU-System-Information,
GNB-CU-Name,
GNB-DU-Name,
InactivityMonitoringRequest,
InactivityMonitoringResponse,
LowerLayerPresenceStatusChange,
NotificationControl,
NRCGI,
NRPCI,
UEContextNotRetrievable,
Potential-SpCell-Item,
RAT-FrequencyPriorityInformation,
RequestedSRSTransmissionCharacteristics,
ResourceCoordinationTransferContainer,
RRCContainer,
RRCContainer-RRCSetupComplete,
RRCReconfigurationCompleteIndicator,
SCellIndex,
SCell-ToBeRemoved-Item,
SCell-ToBeSetup-Item,
SCell-ToBeSetupMod-Item,
SCell-FailedtoSetup-Item,
SCell-FailedtoSetupMod-Item,
ServCellIndex,
Served-Cell-Information,
Served-Cells-To-Add-Item,
Served-Cells-To-Delete-Item,
Served-Cells-To-Modify-Item,
ServingCellMO,
SRBID,
SRBs-FailedToBeSetup-Item,
SRBs-FailedToBeSetupMod-Item,
SRBs-Required-ToBeReleased-Item,
SRBs-ToBeReleased-Item,
SRBs-ToBeSetup-Item,
SRBs-ToBeSetupMod-Item,
SRBs-Modified-Item,
SRBs-Setup-Item,
SRBs-SetupMod-Item,
TimeToWait,
TransactionID,
TransmissionActionIndicator,
UE-associatedLogicalF1-ConnectionItem,
DUtoCURRCContainer,
PagingCell-Item,
SItype-List,
UEIdentityIndexValue,
GNB-CU-TNL-Association-Setup-Item,
GNB-CU-TNL-Association-Failed-To-Setup-Item,
GNB-CU-TNL-Association-To-Add-Item,
GNB-CU-TNL-Association-To-Remove-Item,
GNB-CU-TNL-Association-To-Update-Item,
MaskedIMEISV,
PagingDRX,
PagingPriority,
PagingIdentity,
Cells-to-be-Barred-Item,
PWSSystemInformation,
Broadcast-To-Be-Cancelled-Item,
Cells-Broadcast-Cancelled-Item,
NR-CGI-List-For-Restart-Item,
PWS-Failed-NR-CGI-Item,
RepetitionPeriod,
NumberofBroadcastRequest,
Cells-To-Be-Broadcast-Item,
Cells-Broadcast-Completed-Item,
Cancel-all-Warning-Messages-Indicator,
EUTRA-NR-CellResourceCoordinationReq-Container,
EUTRA-NR-CellResourceCoordinationReqAck-Container,
RequestType,
PLMN-Identity,
RLCFailureIndication,
UplinkTxDirectCurrentListInformation,
SULAccessIndication,
Protected-EUTRA-Resources-Item,
GNB-DUConfigurationQuery,
BitRate,
RRC-Version,
GNBDUOverloadInformation,
RRCDeliveryStatusRequest,
NeedforGap,
RRCDeliveryStatus,
ResourceCoordinationTransferInformation,
Dedicated-SIDelivery-NeededUE-Item,
Associated-SCell-Item,
IgnoreResourceCoordinationContainer,
PagingOrigin,
UAC-Assistance-Info,
RANUEID,
GNB-DU-TNL-Association-To-Remove-Item,
NotificationInformation,
TraceActivation,
TraceID,
Neighbour-Cell-Information-Item,
SymbolAllocInSlot,
NumDLULSymbols,
AdditionalRRMPriorityIndex,
DUCURadioInformationType,
CUDURadioInformationType,
Transport-Layer-Address-Info,
BHChannels-ToBeSetup-Item,
BHChannels-Setup-Item,
BHChannels-FailedToBeSetup-Item,
BHChannels-ToBeModified-Item,
BHChannels-ToBeReleased-Item,
BHChannels-ToBeSetupMod-Item,
BHChannels-FailedToBeModified-Item,
BHChannels-FailedToBeSetupMod-Item,
BHChannels-Modified-Item,
BHChannels-SetupMod-Item,
BHChannels-Required-ToBeReleased-Item,
BAPAddress,
BAPPathID,
BAPRoutingID,
BH-Routing-Information-Added-List-Item,
BH-Routing-Information-Removed-List-Item,
Child-Nodes-List,
Child-Nodes-List-Item,
Child-Node-Cells-List,
Child-Node-Cells-List-Item,
Activated-Cells-to-be-Updated-List,
Activated-Cells-to-be-Updated-List-Item,
UL-BH-Non-UP-Traffic-Mapping,
IABTNLAddressesRequested,
IABIPv6RequestType,
IAB-TNL-Addresses-To-Remove-Item,
IABTNLAddress,
IAB-Allocated-TNL-Address-Item,
IABv4AddressesRequested,
TrafficMappingInfo,
UL-UP-TNL-Information-to-Update-List-Item,
UL-UP-TNL-Address-to-Update-List-Item,
DL-UP-TNL-Address-to-Update-List-Item,
NRV2XServicesAuthorized,
LTEV2XServicesAuthorized,
NRUESidelinkAggregateMaximumBitrate,
LTEUESidelinkAggregateMaximumBitrate,
SLDRBs-SetupMod-Item,
SLDRBs-ModifiedConf-Item,
SLDRBID,
SLDRBs-FailedToBeModified-Item,
SLDRBs-FailedToBeSetup-Item,
SLDRBs-FailedToBeSetupMod-Item,
SLDRBs-Modified-Item,
SLDRBs-Required-ToBeModified-Item,
SLDRBs-Required-ToBeReleased-Item,
SLDRBs-Setup-Item,
SLDRBs-ToBeModified-Item,
SLDRBs-ToBeReleased-Item,
SLDRBs-ToBeSetup-Item,
SLDRBs-ToBeSetupMod-Item,
GNBCUMeasurementID,
GNBDUMeasurementID,
RegistrationRequest,
ReportCharacteristics,
CellToReportList,
HardwareLoadIndicator,
CellMeasurementResultList,
ReportingPeriodicity,
TNLCapacityIndicator,
RACHReportInformationList,
RLFReportInformationList,
ReportingRequestType,
TimeReferenceInformation,
ConditionalInterDUMobilityInformation,
ConditionalIntraDUMobilityInformation,
TargetCellList,
MDTPLMNList,
PrivacyIndicator,
TransportLayerAddress,
URI-address,
NID,
PosAssistance-Information,
PosBroadcast,
PositioningBroadcastCells,
RoutingID,
PosAssistanceInformationFailureList,
PosMeasurementQuantities,
PosMeasurementResultList,
PosReportCharacteristics,
TRPInformationTypeItem,
TRPInformationItem,
LMF-MeasurementID,
RAN-MeasurementID,
SRSResourceSetID,
SpatialRelationInfo,
SRSResourceTrigger,
SRSConfiguration,
TRPList,
E-CID-MeasurementQuantities,
MeasurementPeriodicity,
E-CID-MeasurementResult,
Cell-Portion-ID,
LMF-UE-MeasurementID,
RAN-UE-MeasurementID,
RelativeTime1900,
SystemFrameNumber,
SlotNumber,
AbortTransmission,
TRP-MeasurementRequestList,
MeasurementBeamInfoRequest,
E-CID-ReportCharacteristics,
Extended-GNB-CU-Name,
Extended-GNB-DU-Name,
F1CTransferPath,
SCGIndicator,
SpatialRelationPerSRSResource

FROM F1AP-IEs

PrivateIE-Container{},
ProtocolExtensionContainer{},
ProtocolIE-Container{},
ProtocolIE-ContainerPair{},
ProtocolIE-SingleContainer{},
F1AP-PRIVATE-IES,
F1AP-PROTOCOL-EXTENSION,
F1AP-PROTOCOL-IES,
F1AP-PROTOCOL-IES-PAIR

FROM F1AP-Containers

id-Candidate-SpCell-Item,
id-Candidate-SpCell-List,
id-Cause,
id-Cancel-all-Warning-Messages-Indicator,
id-Cells-Failed-to-be-Activated-List,
id-Cells-Failed-to-be-Activated-List-Item,
id-Cells-Status-Item,
id-Cells-Status-List,
id-Cells-to-be-Activated-List,
id-Cells-to-be-Activated-List-Item,
id-Cells-to-be-Deactivated-List,
id-Cells-to-be-Deactivated-List-Item,
id-ConfirmedUEID,
id-CriticalityDiagnostics,
id-C-RNTI,
id-CUtoDURRCInformation,
id-DRB-Activity-Item,
id-DRB-Activity-List,
id-DRBs-FailedToBeModified-Item,
id-DRBs-FailedToBeModified-List,
id-DRBs-FailedToBeSetup-Item,
id-DRBs-FailedToBeSetup-List,
id-DRBs-FailedToBeSetupMod-Item,
id-DRBs-FailedToBeSetupMod-List,
id-DRBs-ModifiedConf-Item,
id-DRBs-ModifiedConf-List,
id-DRBs-Modified-Item,
id-DRBs-Modified-List,
id-DRB-Notify-Item,
id-DRB-Notify-List,
id-DRBs-Required-ToBeModified-Item,
id-DRBs-Required-ToBeModified-List,
id-DRBs-Required-ToBeReleased-Item,
id-DRBs-Required-ToBeReleased-List,
id-DRBs-Setup-Item,
id-DRBs-Setup-List,
id-DRBs-SetupMod-Item,
id-DRBs-SetupMod-List,
id-DRBs-ToBeModified-Item,
id-DRBs-ToBeModified-List,
id-DRBs-ToBeReleased-Item,
id-DRBs-ToBeReleased-List,
id-DRBs-ToBeSetup-Item,
id-DRBs-ToBeSetup-List,
id-DRBs-ToBeSetupMod-Item,
id-DRBs-ToBeSetupMod-List,
id-DRXCycle,
id-DUtoCURRCInformation,
id-ExecuteDuplication,
id-FullConfiguration,
id-gNB-CU-UE-F1AP-ID,
id-gNB-DU-UE-F1AP-ID,
id-gNB-DU-ID,
id-GNB-DU-Served-Cells-Item,
id-gNB-DU-Served-Cells-List,
id-gNB-CU-Name,
id-gNB-DU-Name,
id-Extended-GNB-CU-Name,
id-Extended-GNB-DU-Name,
id-InactivityMonitoringRequest,
id-InactivityMonitoringResponse,
id-new-gNB-CU-UE-F1AP-ID,
id-new-gNB-DU-UE-F1AP-ID,
id-oldgNB-DU-UE-F1AP-ID,
id-PLMNAssistanceInfoForNetShar,
id-Potential-SpCell-Item,
id-Potential-SpCell-List,
id-RAT-FrequencyPriorityInformation,
id-RedirectedRRCmessage,
id-ResetType,
id-RequestedSRSTransmissionCharacteristics,
id-ResourceCoordinationTransferContainer,
id-RRCContainer,
id-RRCContainer-RRCSetupComplete,
id-RRCReconfigurationCompleteIndicator,
id-SCell-FailedtoSetup-List,
id-SCell-FailedtoSetup-Item,
id-SCell-FailedtoSetupMod-List,
id-SCell-FailedtoSetupMod-Item,
id-SCell-ToBeRemoved-Item,
id-SCell-ToBeRemoved-List,
id-SCell-ToBeSetup-Item,
id-SCell-ToBeSetup-List,
id-SCell-ToBeSetupMod-Item,
id-SCell-ToBeSetupMod-List,
id-SelectedPLMNID,
id-Served-Cells-To-Add-Item,
id-Served-Cells-To-Add-List,
id-Served-Cells-To-Delete-Item,
id-Served-Cells-To-Delete-List,
id-Served-Cells-To-Modify-Item,
id-Served-Cells-To-Modify-List,
id-ServCellIndex,
id-ServingCellMO,
id-SpCell-ID,
id-SpCellULConfigured,
id-SRBID,
id-SRBs-FailedToBeSetup-Item,
id-SRBs-FailedToBeSetup-List,
id-SRBs-FailedToBeSetupMod-Item,
id-SRBs-FailedToBeSetupMod-List,
id-SRBs-Required-ToBeReleased-Item,
id-SRBs-Required-ToBeReleased-List,
id-SRBs-ToBeReleased-Item,
id-SRBs-ToBeReleased-List,
id-SRBs-ToBeSetup-Item,
id-SRBs-ToBeSetup-List,
id-SRBs-ToBeSetupMod-Item,
id-SRBs-ToBeSetupMod-List,
id-SRBs-Modified-Item,
id-SRBs-Modified-List,
id-SRBs-Setup-Item,
id-SRBs-Setup-List,
id-SRBs-SetupMod-Item,
id-SRBs-SetupMod-List,
id-TimeToWait,
id-TransactionID,
id-TransmissionActionIndicator,
id-UEContextNotRetrievable,
id-UE-associatedLogicalF1-ConnectionItem,
id-UE-associatedLogicalF1-ConnectionListResAck,
id-DUtoCURRCContainer,
id-NRCGI,
id-PagingCell-Item,
id-PagingCell-List,
id-PagingDRX,
id-PagingPriority,
id-SItype-List,
id-UEIdentityIndexValue,
id-GNB-CU-TNL-Association-Setup-List,
id-GNB-CU-TNL-Association-Setup-Item,
id-GNB-CU-TNL-Association-Failed-To-Setup-List,
id-GNB-CU-TNL-Association-Failed-To-Setup-Item,
id-GNB-CU-TNL-Association-To-Add-Item,
id-GNB-CU-TNL-Association-To-Add-List,
id-GNB-CU-TNL-Association-To-Remove-Item,
id-GNB-CU-TNL-Association-To-Remove-List,
id-GNB-CU-TNL-Association-To-Update-Item,
id-GNB-CU-TNL-Association-To-Update-List,
id-MaskedIMEISV,
id-PagingIdentity,
id-Cells-to-be-Barred-List,
id-Cells-to-be-Barred-Item,
id-PWSSystemInformation,
id-RepetitionPeriod,
id-NumberofBroadcastRequest,
id-Cells-To-Be-Broadcast-List,
id-Cells-To-Be-Broadcast-Item,
id-Cells-Broadcast-Completed-List,
id-Cells-Broadcast-Completed-Item,
id-Broadcast-To-Be-Cancelled-List,
id-Broadcast-To-Be-Cancelled-Item,
id-Cells-Broadcast-Cancelled-List,
id-Cells-Broadcast-Cancelled-Item,
id-NR-CGI-List-For-Restart-List,
id-NR-CGI-List-For-Restart-Item,
id-PWS-Failed-NR-CGI-List,
id-PWS-Failed-NR-CGI-Item,
id-EUTRA-NR-CellResourceCoordinationReq-Container,
id-EUTRA-NR-CellResourceCoordinationReqAck-Container,
id-Protected-EUTRA-Resources-List,
id-RequestType,
id-ServingPLMN,
id-DRXConfigurationIndicator,
id-RLCFailureIndication,
id-UplinkTxDirectCurrentListInformation,
id-SULAccessIndication,
id-Protected-EUTRA-Resources-Item,
id-GNB-DUConfigurationQuery,
id-GNB-DU-UE-AMBR-UL,
id-GNB-CU-RRC-Version,
id-GNB-DU-RRC-Version,
id-GNBDUOverloadInformation,
id-NeedforGap,
id-RRCDeliveryStatusRequest,
id-RRCDeliveryStatus,
id-Dedicated-SIDelivery-NeededUE-List,
id-Dedicated-SIDelivery-NeededUE-Item,
id-ResourceCoordinationTransferInformation,
id-Associated-SCell-List,
id-Associated-SCell-Item,
id-IgnoreResourceCoordinationContainer,
id-UAC-Assistance-Info,
id-RANUEID,
id-PagingOrigin,
id-GNB-DU-TNL-Association-To-Remove-Item,
id-GNB-DU-TNL-Association-To-Remove-List,
id-NotificationInformation,
id-TraceActivation,
id-TraceID,
id-Neighbour-Cell-Information-List,
id-Neighbour-Cell-Information-Item,
id-SymbolAllocInSlot,
id-NumDLULSymbols,
id-AdditionalRRMPriorityIndex,
id-DUCURadioInformationType,
id-CUDURadioInformationType,
id-LowerLayerPresenceStatusChange,
id-Transport-Layer-Address-Info,
id-BHChannels-ToBeSetup-List,
id-BHChannels-ToBeSetup-Item,
id-BHChannels-Setup-List,
id-BHChannels-Setup-Item,
id-BHChannels-ToBeModified-Item,
id-BHChannels-ToBeModified-List,
id-BHChannels-ToBeReleased-Item,
id-BHChannels-ToBeReleased-List,
id-BHChannels-ToBeSetupMod-Item,
id-BHChannels-ToBeSetupMod-List,
id-BHChannels-FailedToBeSetup-Item,
id-BHChannels-FailedToBeSetup-List,
id-BHChannels-FailedToBeModified-Item,
id-BHChannels-FailedToBeModified-List,
id-BHChannels-FailedToBeSetupMod-Item,
id-BHChannels-FailedToBeSetupMod-List,
id-BHChannels-Modified-Item,
id-BHChannels-Modified-List,
id-BHChannels-SetupMod-Item,
id-BHChannels-SetupMod-List,
id-BHChannels-Required-ToBeReleased-Item,
id-BHChannels-Required-ToBeReleased-List,
id-BAPAddress,
id-ConfiguredBAPAddress,
id-BH-Routing-Information-Added-List,
id-BH-Routing-Information-Added-List-Item,
id-BH-Routing-Information-Removed-List,
id-BH-Routing-Information-Removed-List-Item,
id-UL-BH-Non-UP-Traffic-Mapping,
id-Child-Nodes-List,
id-Activated-Cells-to-be-Updated-List,
id-IABIPv6RequestType,
id-IAB-TNL-Addresses-To-Remove-List,
id-IAB-TNL-Addresses-To-Remove-Item,
id-IAB-Allocated-TNL-Address-List,
id-IAB-Allocated-TNL-Address-Item,
id-IABv4AddressesRequested,
id-TrafficMappingInformation,
id-UL-UP-TNL-Information-to-Update-List,
id-UL-UP-TNL-Information-to-Update-List-Item,
id-UL-UP-TNL-Address-to-Update-List,
id-UL-UP-TNL-Address-to-Update-List-Item,
id-DL-UP-TNL-Address-to-Update-List,
id-DL-UP-TNL-Address-to-Update-List-Item,
id-NRV2XServicesAuthorized,
id-LTEV2XServicesAuthorized,
id-NRUESidelinkAggregateMaximumBitrate,
id-LTEUESidelinkAggregateMaximumBitrate,
id-PC5LinkAMBR,
id-SLDRBs-FailedToBeModified-Item,
id-SLDRBs-FailedToBeModified-List,
id-SLDRBs-FailedToBeSetup-Item,
id-SLDRBs-FailedToBeSetup-List,
id-SLDRBs-Modified-Item,
id-SLDRBs-Modified-List,
id-SLDRBs-Required-ToBeModified-Item,
id-SLDRBs-Required-ToBeModified-List,
id-SLDRBs-Required-ToBeReleased-Item,
id-SLDRBs-Required-ToBeReleased-List,
id-SLDRBs-Setup-Item,
id-SLDRBs-Setup-List,
id-SLDRBs-ToBeModified-Item,
id-SLDRBs-ToBeModified-List,
id-SLDRBs-ToBeReleased-Item,
id-SLDRBs-ToBeReleased-List,
id-SLDRBs-ToBeSetup-Item,
id-SLDRBs-ToBeSetup-List,
id-SLDRBs-ToBeSetupMod-Item,
id-SLDRBs-ToBeSetupMod-List,
id-SLDRBs-SetupMod-List,
id-SLDRBs-FailedToBeSetupMod-List,
id-SLDRBs-SetupMod-Item,
id-SLDRBs-FailedToBeSetupMod-Item,
id-SLDRBs-ModifiedConf-List,
id-SLDRBs-ModifiedConf-Item,
id-gNBCUMeasurementID,
id-gNBDUMeasurementID,
id-RegistrationRequest,
id-ReportCharacteristics,
id-CellToReportList,
id-CellMeasurementResultList,
id-HardwareLoadIndicator,
id-ReportingPeriodicity,
id-TNLCapacityIndicator,
id-RACHReportInformationList,
id-RLFReportInformationList,
id-ReportingRequestType,
id-TimeReferenceInformation,
id-ConditionalInterDUMobilityInformation,
id-ConditionalIntraDUMobilityInformation,
id-targetCellsToCancel,
id-requestedTargetCellGlobalID,
id-TraceCollectionEntityIPAddress,
id-ManagementBasedMDTPLMNList,
id-PrivacyIndicator,
id-TraceCollectionEntityURI,
id-ServingNID,
id-PosAssistance-Information,
id-PosBroadcast,
id-PositioningBroadcastCells,
id-RoutingID,
id-PosAssistanceInformationFailureList,
id-PosMeasurementQuantities,
id-PosMeasurementResultList,
id-PosMeasurementPeriodicity,
id-PosReportCharacteristics,
id-TRPInformationTypeListTRPReq,
id-TRPInformationTypeItem,
id-TRPInformationListTRPResp,
id-TRPInformationItem,
id-LMF-MeasurementID,
id-RAN-MeasurementID,
id-SRSType,
id-ActivationTime,
id-AbortTransmission,
id-SRSConfiguration,
id-TRPList,
id-E-CID-MeasurementQuantities,
id-E-CID-MeasurementPeriodicity,
id-E-CID-MeasurementResult,
id-Cell-Portion-ID,
id-LMF-UE-MeasurementID,
id-RAN-UE-MeasurementID,
id-SFNInitialisationTime,
id-SystemFrameNumber,
id-SlotNumber,
id-TRP-MeasurementRequestList,
id-MeasurementBeamInfoRequest,
id-E-CID-ReportCharacteristics,
id-F1CTransferPath,
id-SCGIndicator,
id-SRSSpatialRelationPerSRSResource,
maxCellingNBDU,
maxnoofCandidateSpCells,
maxnoofDRBs,
maxnoofErrors,
maxnoofIndividualF1ConnectionsToReset,
maxnoofPotentialSpCells,
maxnoofSCells,
maxnoofSRBs,
maxnoofPagingCells,
maxnoofTNLAssociations,
maxCellineNB,
maxnoofUEIDs,
maxnoofBHRLCChannels,
maxnoofRoutingEntries,
maxnoofChildIABNodes,
maxnoofServedCellsIAB,
maxnoofTLAsIAB,
maxnoofULUPTNLInformationforIAB,
maxnoofUPTNLAddresses,
maxnoofSLDRBs,
maxnoofTRPInfoTypes,
maxnoofTRPs

FROM F1AP-Constants;

-- **************************************************************
--
-- RESET ELEMENTARY PROCEDURE
--
-- **************************************************************

-- **************************************************************
--
-- Reset
--
-- **************************************************************

Reset ::= SEQUENCE {
   protocolIEs ProtocolIE-Container { {ResetIEs} },
   ...
}

ResetIEs F1AP-PROTOCOL-IES ::= {
   { ID id-TransactionID CRITICALITY reject TYPE TransactionID PRESENCE mandatory }|
   { ID id-Cause CRITICALITY ignore TYPE Cause PRESENCE mandatory }|
   { ID id-ResetType CRITICALITY reject TYPE ResetType PRESENCE mandatory },
   ...
}

ResetType ::= CHOICE {
   f1-Interface ResetAll,
   partOfF1-Interface UE-associatedLogicalF1-ConnectionListRes,
   choice-extension ProtocolIE-SingleContainer { { ResetType-ExtIEs} }
}

ResetType-ExtIEs F1AP-PROTOCOL-IES ::= {
   ...
}

ResetAll ::= ENUMERATED {
   reset-all,
   ...
}

UE-associatedLogicalF1-ConnectionListRes ::= SEQUENCE (SIZE(1.. maxnoofIndividualF1ConnectionsToReset)) OF ProtocolIE-SingleContainer { { UE-associatedLogicalF1-ConnectionItemRes } }

UE-associatedLogicalF1-ConnectionItemRes F1AP-PROTOCOL-IES ::= {
   { ID id-UE-associatedLogicalF1-ConnectionItem CRITICALITY reject TYPE UE-associatedLogicalF1-ConnectionItem PRESENCE mandatory},
   ...
}

-- **************************************************************
--
-- Reset Acknowledge
--
-- **************************************************************

ResetAcknowledge ::= SEQUENCE {
   protocolIEs ProtocolIE-Container { {ResetAcknowledgeIEs} },
   ...
}

ResetAcknowledgeIEs F1AP-PROTOCOL-IES ::= {
   { ID id-TransactionID CRITICALITY reject TYPE TransactionID PRESENCE mandatory }|
   { ID id-UE-associatedLogicalF1-ConnectionListResAck CRITICALITY ignore TYPE UE-associatedLogicalF1-ConnectionListResAck PRESENCE optional }|
   { ID id-CriticalityDiagnostics CRITICALITY ignore TYPE CriticalityDiagnostics PRESENCE optional },
   ...
}

UE-associatedLogicalF1-ConnectionListResAck ::= SEQUENCE (SIZE(1.. maxnoofIndividualF1ConnectionsToReset)) OF ProtocolIE-SingleContainer { { UE-associatedLogicalF1-ConnectionItemResAck } }

UE-associatedLogicalF1-ConnectionItemResAck F1AP-PROTOCOL-IES ::= {
   { ID id-UE-associatedLogicalF1-ConnectionItem CRITICALITY ignore TYPE UE-associatedLogicalF1-ConnectionItem PRESENCE mandatory },
   ...
}

-- **************************************************************
--
-- ERROR INDICATION ELEMENTARY PROCEDURE
--
-- **************************************************************

-- **************************************************************
--
-- Error Indication
--
-- **************************************************************

ErrorIndication ::= SEQUENCE {
   protocolIEs ProtocolIE-Container {{ErrorIndicationIEs}},
   ...
}

ErrorIndicationIEs F1AP-PROTOCOL-IES ::= {
   { ID id-TransactionID CRITICALITY reject TYPE TransactionID PRESENCE mandatory}|
   { ID id-gNB-CU-UE-F1AP-ID CRITICALITY ignore TYPE GNB-CU-UE-F1AP-ID PRESENCE optional }|
   { ID id-gNB-DU-UE-F1AP-ID CRITICALITY ignore TYPE GNB-DU-UE-F1AP-ID PRESENCE optional }|
   { ID id-Cause CRITICALITY ignore TYPE Cause PRESENCE optional }|
   { ID id-CriticalityDiagnostics CRITICALITY ignore TYPE CriticalityDiagnostics PRESENCE optional },
   ...
}

-- **************************************************************
--
-- F1 SETUP ELEMENTARY PROCEDURE
--
-- **************************************************************

-- **************************************************************
--
-- F1 Setup Request
--
-- **************************************************************

F1SetupRequest ::= SEQUENCE {
   protocolIEs ProtocolIE-Container { {F1SetupRequestIEs} },
   ...
}

F1SetupRequestIEs F1AP-PROTOCOL-IES ::= {
   { ID id-TransactionID CRITICALITY reject TYPE TransactionID PRESENCE mandatory }|
   { ID id-gNB-DU-ID CRITICALITY reject TYPE GNB-DU-ID PRESENCE mandatory }|
   { ID id-gNB-DU-Name CRITICALITY ignore TYPE GNB-DU-Name PRESENCE optional }|
   { ID id-gNB-DU-Served-Cells-List CRITICALITY reject TYPE GNB-DU-Served-Cells-List PRESENCE optional }|
   { ID id-GNB-DU-RRC-Version CRITICALITY reject TYPE RRC-Version PRESENCE mandatory }|
   { ID id-Transport-Layer-Address-Info CRITICALITY ignore TYPE Transport-Layer-Address-Info PRESENCE optional }|
   { ID id-BAPAddress CRITICALITY ignore TYPE BAPAddress PRESENCE optional }|
   { ID id-Extended-GNB-DU-Name CRITICALITY ignore TYPE Extended-GNB-DU-Name PRESENCE optional },
   ...
}

GNB-DU-Served-Cells-List ::= SEQUENCE (SIZE(1.. maxCellingNBDU)) OF ProtocolIE-SingleContainer { { GNB-DU-Served-Cells-ItemIEs } }

GNB-DU-Served-Cells-ItemIEs F1AP-PROTOCOL-IES ::= {
   { ID id-GNB-DU-Served-Cells-Item CRITICALITY reject TYPE GNB-DU-Served-Cells-Item PRESENCE mandatory },
   ...
}

-- **************************************************************
--
-- F1 Setup Response
--
-- **************************************************************

F1SetupResponse ::= SEQUENCE {
   protocolIEs ProtocolIE-Container { {F1SetupResponseIEs} },
   ...
}

F1SetupResponseIEs F1AP-PROTOCOL-IES ::= {
   { ID id-TransactionID CRITICALITY reject TYPE TransactionID PRESENCE mandatory }|
   { ID id-gNB-CU-Name CRITICALITY ignore TYPE GNB-CU-Name PRESENCE optional }|
   { ID id-Cells-to-be-Activated-List CRITICALITY reject TYPE Cells-to-be-Activated-List PRESENCE optional }|
   { ID id-GNB-CU-RRC-Version CRITICALITY reject TYPE RRC-Version PRESENCE mandatory }|
   { ID id-Transport-Layer-Address-Info CRITICALITY ignore TYPE Transport-Layer-Address-Info PRESENCE optional }|
   { ID id-UL-BH-Non-UP-Traffic-Mapping CRITICALITY reject TYPE UL-BH-Non-UP-Traffic-Mapping PRESENCE optional }|
   { ID id-BAPAddress CRITICALITY ignore TYPE BAPAddress PRESENCE optional }|
   { ID id-Extended-GNB-CU-Name CRITICALITY ignore TYPE Extended-GNB-CU-Name PRESENCE optional },
   ...
}

Cells-to-be-Activated-List ::= SEQUENCE (SIZE(1.. maxCellingNBDU)) OF ProtocolIE-SingleContainer { { Cells-to-be-Activated-List-ItemIEs } }

Cells-to-be-Activated-List-ItemIEs F1AP-PROTOCOL-IES::= {
   { ID id-Cells-to-be-Activated-List-Item CRITICALITY reject TYPE Cells-to-be-Activated-List-Item PRESENCE mandatory},
   ...
}

-- **************************************************************
--
-- F1 Setup Failure
--
-- **************************************************************

F1SetupFailure ::= SEQUENCE {
   protocolIEs ProtocolIE-Container { {F1SetupFailureIEs} },
   ...
}

F1SetupFailureIEs F1AP-PROTOCOL-IES ::= {
   { ID id-TransactionID CRITICALITY reject TYPE TransactionID PRESENCE mandatory }|
   { ID id-Cause CRITICALITY ignore TYPE Cause PRESENCE mandatory }|
   { ID id-TimeToWait CRITICALITY ignore TYPE TimeToWait PRESENCE optional }|
   { ID id-CriticalityDiagnostics CRITICALITY ignore TYPE CriticalityDiagnostics PRESENCE optional },
   ...
}

-- **************************************************************
--
-- GNB-DU CONFIGURATION UPDATE ELEMENTARY PROCEDURE
--
-- **************************************************************

-- **************************************************************
--
-- GNB-DU CONFIGURATION UPDATE
--
-- **************************************************************

GNBDUConfigurationUpdate::= SEQUENCE {
   protocolIEs ProtocolIE-Container { {GNBDUConfigurationUpdateIEs} },
   ...
}

GNBDUConfigurationUpdateIEs F1AP-PROTOCOL-IES ::= {
   { ID id-TransactionID CRITICALITY reject TYPE TransactionID PRESENCE mandatory }|
   { ID id-Served-Cells-To-Add-List CRITICALITY reject TYPE Served-Cells-To-Add-List PRESENCE optional }|
   { ID id-Served-Cells-To-Modify-List CRITICALITY reject TYPE Served-Cells-To-Modify-List PRESENCE optional }|
   { ID id-Served-Cells-To-Delete-List CRITICALITY reject TYPE Served-Cells-To-Delete-List PRESENCE optional }|
   { ID id-Cells-Status-List CRITICALITY reject TYPE Cells-Status-List PRESENCE optional }|
   { ID id-Dedicated-SIDelivery-NeededUE-List CRITICALITY ignore TYPE Dedicated-SIDelivery-NeededUE-List PRESENCE optional }|
   { ID id-gNB-DU-ID CRITICALITY reject TYPE GNB-DU-ID PRESENCE optional }|
   { ID id-GNB-DU-TNL-Association-To-Remove-List CRITICALITY reject TYPE GNB-DU-TNL-Association-To-Remove-List PRESENCE optional }|
   { ID id-Transport-Layer-Address-Info CRITICALITY ignore TYPE Transport-Layer-Address-Info PRESENCE optional },
   ...
}

Served-Cells-To-Add-List ::= SEQUENCE (SIZE(1.. maxCellingNBDU)) OF ProtocolIE-SingleContainer { { Served-Cells-To-Add-ItemIEs } }
Served-Cells-To-Modify-List ::= SEQUENCE (SIZE(1.. maxCellingNBDU)) OF ProtocolIE-SingleContainer { { Served-Cells-To-Modify-ItemIEs } }
Served-Cells-To-Delete-List ::= SEQUENCE (SIZE(1.. maxCellingNBDU)) OF ProtocolIE-SingleContainer { { Served-Cells-To-Delete-ItemIEs } }
Cells-Status-List ::= SEQUENCE (SIZE(0.. maxCellingNBDU)) OF ProtocolIE-SingleContainer { { Cells-Status-ItemIEs } }

Dedicated-SIDelivery-NeededUE-List::= SEQUENCE (SIZE(1.. maxnoofUEIDs)) OF ProtocolIE-SingleContainer { { Dedicated-SIDelivery-NeededUE-ItemIEs } }

GNB-DU-TNL-Association-To-Remove-List ::= SEQUENCE (SIZE(1.. maxnoofTNLAssociations)) OF ProtocolIE-SingleContainer { { GNB-DU-TNL-Association-To-Remove-ItemIEs } }

Served-Cells-To-Add-ItemIEs F1AP-PROTOCOL-IES ::= {
   { ID id-Served-Cells-To-Add-Item CRITICALITY reject TYPE Served-Cells-To-Add-Item PRESENCE mandatory },
   ...
}

Served-Cells-To-Modify-ItemIEs F1AP-PROTOCOL-IES ::= {
   { ID id-Served-Cells-To-Modify-Item CRITICALITY reject TYPE Served-Cells-To-Modify-Item PRESENCE mandatory },
   ...
}

Served-Cells-To-Delete-ItemIEs F1AP-PROTOCOL-IES ::= {
   { ID id-Served-Cells-To-Delete-Item CRITICALITY reject TYPE Served-Cells-To-Delete-Item PRESENCE mandatory },
   ...
}

Cells-Status-ItemIEs F1AP-PROTOCOL-IES ::= {
   { ID id-Cells-Status-Item CRITICALITY reject TYPE Cells-Status-Item PRESENCE mandatory },
   ...
}

Dedicated-SIDelivery-NeededUE-ItemIEs F1AP-PROTOCOL-IES ::= {
   { ID id-Dedicated-SIDelivery-NeededUE-Item CRITICALITY ignore TYPE Dedicated-SIDelivery-NeededUE-Item PRESENCE mandatory },
   ...
}

GNB-DU-TNL-Association-To-Remove-ItemIEs F1AP-PROTOCOL-IES ::= {
   { ID id-GNB-DU-TNL-Association-To-Remove-Item CRITICALITY reject TYPE GNB-DU-TNL-Association-To-Remove-Item PRESENCE mandatory },
   ...
}

-- **************************************************************
--
-- GNB-DU CONFIGURATION UPDATE ACKNOWLEDGE
--
-- **************************************************************

GNBDUConfigurationUpdateAcknowledge ::= SEQUENCE {
   protocolIEs ProtocolIE-Container { {GNBDUConfigurationUpdateAcknowledgeIEs} },
   ...
}

GNBDUConfigurationUpdateAcknowledgeIEs F1AP-PROTOCOL-IES ::= {
   { ID id-TransactionID CRITICALITY reject TYPE TransactionID PRESENCE mandatory }|
   { ID id-Cells-to-be-Activated-List CRITICALITY reject TYPE Cells-to-be-Activated-List PRESENCE optional }|
   { ID id-CriticalityDiagnostics CRITICALITY ignore TYPE CriticalityDiagnostics PRESENCE optional }|
   { ID id-Cells-to-be-Deactivated-List CRITICALITY reject TYPE Cells-to-be-Deactivated-List PRESENCE optional }|
   { ID id-Transport-Layer-Address-Info CRITICALITY ignore TYPE Transport-Layer-Address-Info PRESENCE optional }|
   { ID id-UL-BH-Non-UP-Traffic-Mapping CRITICALITY reject TYPE UL-BH-Non-UP-Traffic-Mapping PRESENCE optional }|
   { ID id-BAPAddress CRITICALITY ignore TYPE BAPAddress PRESENCE optional },
   ...
}

-- **************************************************************
--
-- GNB-DU CONFIGURATION UPDATE FAILURE
--
-- **************************************************************

GNBDUConfigurationUpdateFailure ::= SEQUENCE {
   protocolIEs ProtocolIE-Container { {GNBDUConfigurationUpdateFailureIEs} },
   ...
}

GNBDUConfigurationUpdateFailureIEs F1AP-PROTOCOL-IES ::= {
   { ID id-TransactionID CRITICALITY reject TYPE TransactionID PRESENCE mandatory }|
   { ID id-Cause CRITICALITY ignore TYPE Cause PRESENCE mandatory }|
   { ID id-TimeToWait CRITICALITY ignore TYPE TimeToWait PRESENCE optional }|
   { ID id-CriticalityDiagnostics CRITICALITY ignore TYPE CriticalityDiagnostics PRESENCE optional },
   ...
}

-- **************************************************************
--
-- GNB-CU CONFIGURATION UPDATE ELEMENTARY PROCEDURE
--
-- **************************************************************

-- **************************************************************
--
-- GNB-CU CONFIGURATION UPDATE
--
-- **************************************************************

GNBCUConfigurationUpdate ::= SEQUENCE {
   protocolIEs ProtocolIE-Container { { GNBCUConfigurationUpdateIEs} },
   ...
}

GNBCUConfigurationUpdateIEs F1AP-PROTOCOL-IES ::= {
   { ID id-TransactionID CRITICALITY reject TYPE TransactionID PRESENCE mandatory }|
   { ID id-Cells-to-be-Activated-List CRITICALITY reject TYPE Cells-to-be-Activated-List PRESENCE optional }|
   { ID id-Cells-to-be-Deactivated-List CRITICALITY reject TYPE Cells-to-be-Deactivated-List PRESENCE optional }|
   { ID id-GNB-CU-TNL-Association-To-Add-List CRITICALITY ignore TYPE GNB-CU-TNL-Association-To-Add-List PRESENCE optional }|
   { ID id-GNB-CU-TNL-Association-To-Remove-List CRITICALITY ignore TYPE GNB-CU-TNL-Association-To-Remove-List PRESENCE optional }|
   { ID id-GNB-CU-TNL-Association-To-Update-List CRITICALITY ignore TYPE GNB-CU-TNL-Association-To-Update-List PRESENCE optional }|
   { ID id-Cells-to-be-Barred-List CRITICALITY ignore TYPE Cells-to-be-Barred-List PRESENCE optional }|
   { ID id-Protected-EUTRA-Resources-List CRITICALITY reject TYPE Protected-EUTRA-Resources-List PRESENCE optional }|
   { ID id-Neighbour-Cell-Information-List CRITICALITY ignore TYPE Neighbour-Cell-Information-List PRESENCE optional }|
   { ID id-Transport-Layer-Address-Info CRITICALITY ignore TYPE Transport-Layer-Address-Info PRESENCE optional }|
   { ID id-UL-BH-Non-UP-Traffic-Mapping CRITICALITY reject TYPE UL-BH-Non-UP-Traffic-Mapping PRESENCE optional }|
   { ID id-BAPAddress CRITICALITY ignore TYPE BAPAddress PRESENCE optional },
   ...
}

Cells-to-be-Deactivated-List ::= SEQUENCE (SIZE(1.. maxCellingNBDU)) OF ProtocolIE-SingleContainer { { Cells-to-be-Deactivated-List-ItemIEs } }
GNB-CU-TNL-Association-To-Add-List ::= SEQUENCE (SIZE(1.. maxnoofTNLAssociations)) OF ProtocolIE-SingleContainer { { GNB-CU-TNL-Association-To-Add-ItemIEs } }
GNB-CU-TNL-Association-To-Remove-List ::= SEQUENCE (SIZE(1.. maxnoofTNLAssociations)) OF ProtocolIE-SingleContainer { { GNB-CU-TNL-Association-To-Remove-ItemIEs } }
GNB-CU-TNL-Association-To-Update-List ::= SEQUENCE (SIZE(1.. maxnoofTNLAssociations)) OF ProtocolIE-SingleContainer { { GNB-CU-TNL-Association-To-Update-ItemIEs } }
Cells-to-be-Barred-List ::= SEQUENCE(SIZE(1.. maxCellingNBDU)) OF ProtocolIE-SingleContainer { { Cells-to-be-Barred-ItemIEs } }

Cells-to-be-Deactivated-List-ItemIEs F1AP-PROTOCOL-IES ::= {
   { ID id-Cells-to-be-Deactivated-List-Item CRITICALITY reject TYPE Cells-to-be-Deactivated-List-Item PRESENCE mandatory },
   ...
}

GNB-CU-TNL-Association-To-Add-ItemIEs F1AP-PROTOCOL-IES ::= {
   { ID id-GNB-CU-TNL-Association-To-Add-Item CRITICALITY ignore TYPE GNB-CU-TNL-Association-To-Add-Item PRESENCE mandatory },
   ...
}

GNB-CU-TNL-Association-To-Remove-ItemIEs F1AP-PROTOCOL-IES ::= {
   { ID id-GNB-CU-TNL-Association-To-Remove-Item CRITICALITY ignore TYPE GNB-CU-TNL-Association-To-Remove-Item PRESENCE mandatory },
   ...
}

GNB-CU-TNL-Association-To-Update-ItemIEs F1AP-PROTOCOL-IES ::= {
   { ID id-GNB-CU-TNL-Association-To-Update-Item CRITICALITY ignore TYPE GNB-CU-TNL-Association-To-Update-Item PRESENCE mandatory },
   ...
}

Cells-to-be-Barred-ItemIEs F1AP-PROTOCOL-IES ::= {
   { ID id-Cells-to-be-Barred-Item CRITICALITY ignore TYPE Cells-to-be-Barred-Item PRESENCE mandatory },
   ...
}

Protected-EUTRA-Resources-List ::= SEQUENCE (SIZE(1.. maxCellineNB)) OF ProtocolIE-SingleContainer { { Protected-EUTRA-Resources-ItemIEs } }
Protected-EUTRA-Resources-ItemIEs F1AP-PROTOCOL-IES ::= {
   { ID id-Protected-EUTRA-Resources-Item CRITICALITY reject TYPE Protected-EUTRA-Resources-Item PRESENCE mandatory},
   ...
}

Neighbour-Cell-Information-List ::= SEQUENCE (SIZE(1.. maxCellingNBDU)) OF ProtocolIE-SingleContainer { { Neighbour-Cell-Information-ItemIEs } }
Neighbour-Cell-Information-ItemIEs F1AP-PROTOCOL-IES ::= {
   { ID id-Neighbour-Cell-Information-Item CRITICALITY ignore TYPE Neighbour-Cell-Information-Item PRESENCE mandatory},
   ...
}

-- **************************************************************
--
-- GNB-CU CONFIGURATION UPDATE ACKNOWLEDGE
--
-- **************************************************************

GNBCUConfigurationUpdateAcknowledge ::= SEQUENCE {
   protocolIEs ProtocolIE-Container { { GNBCUConfigurationUpdateAcknowledgeIEs} },
   ...
}

GNBCUConfigurationUpdateAcknowledgeIEs F1AP-PROTOCOL-IES ::= {
   { ID id-TransactionID CRITICALITY reject TYPE TransactionID PRESENCE mandatory }|
   { ID id-Cells-Failed-to-be-Activated-List CRITICALITY reject TYPE Cells-Failed-to-be-Activated-List PRESENCE optional}|
   { ID id-CriticalityDiagnostics CRITICALITY ignore TYPE CriticalityDiagnostics PRESENCE optional }|
   { ID id-GNB-CU-TNL-Association-Setup-List CRITICALITY ignore TYPE GNB-CU-TNL-Association-Setup-List PRESENCE optional }|
   { ID id-GNB-CU-TNL-Association-Failed-To-Setup-List CRITICALITY ignore TYPE GNB-CU-TNL-Association-Failed-To-Setup-List PRESENCE optional }|
   { ID id-Dedicated-SIDelivery-NeededUE-List CRITICALITY ignore TYPE Dedicated-SIDelivery-NeededUE-List PRESENCE optional }|
   { ID id-Transport-Layer-Address-Info CRITICALITY ignore TYPE Transport-Layer-Address-Info PRESENCE optional },
   ...
}

Cells-Failed-to-be-Activated-List ::= SEQUENCE (SIZE(1.. maxCellingNBDU)) OF ProtocolIE-SingleContainer { { Cells-Failed-to-be-Activated-List-ItemIEs } }
GNB-CU-TNL-Association-Setup-List ::= SEQUENCE (SIZE(1.. maxnoofTNLAssociations)) OF ProtocolIE-SingleContainer { { GNB-CU-TNL-Association-Setup-ItemIEs } }
GNB-CU-TNL-Association-Failed-To-Setup-List ::= SEQUENCE (SIZE(1.. maxnoofTNLAssociations)) OF ProtocolIE-SingleContainer { { GNB-CU-TNL-Association-Failed-To-Setup-ItemIEs } }

Cells-Failed-to-be-Activated-List-ItemIEs F1AP-PROTOCOL-IES ::= {
   { ID id-Cells-Failed-to-be-Activated-List-Item CRITICALITY reject TYPE Cells-Failed-to-be-Activated-List-Item PRESENCE mandatory },
   ...
}

GNB-CU-TNL-Association-Setup-ItemIEs F1AP-PROTOCOL-IES ::= {
   { ID id-GNB-CU-TNL-Association-Setup-Item CRITICALITY ignore TYPE GNB-CU-TNL-Association-Setup-Item PRESENCE mandatory },
   ...
}

GNB-CU-TNL-Association-Failed-To-Setup-ItemIEs F1AP-PROTOCOL-IES ::= {
   { ID id-GNB-CU-TNL-Association-Failed-To-Setup-Item CRITICALITY ignore TYPE GNB-CU-TNL-Association-Failed-To-Setup-Item PRESENCE mandatory },
   ...
}

-- **************************************************************
--
-- GNB-CU CONFIGURATION UPDATE FAILURE
--
-- **************************************************************

GNBCUConfigurationUpdateFailure ::= SEQUENCE {
   protocolIEs ProtocolIE-Container { { GNBCUConfigurationUpdateFailureIEs} },
   ...
}

GNBCUConfigurationUpdateFailureIEs F1AP-PROTOCOL-IES ::= {
   { ID id-TransactionID CRITICALITY reject TYPE TransactionID PRESENCE mandatory }|
   { ID id-Cause CRITICALITY ignore TYPE Cause PRESENCE mandatory }|
   { ID id-TimeToWait CRITICALITY ignore TYPE TimeToWait PRESENCE optional }|
   { ID id-CriticalityDiagnostics CRITICALITY ignore TYPE CriticalityDiagnostics PRESENCE optional },
   ...
}

-- **************************************************************
--
-- GNB-DU RESOURCE COORDINATION REQUEST
--
-- **************************************************************

GNBDUResourceCoordinationRequest ::= SEQUENCE {
   protocolIEs ProtocolIE-Container {{GNBDUResourceCoordinationRequest-IEs}},
   ...
}

GNBDUResourceCoordinationRequest-IEs F1AP-PROTOCOL-IES ::= {
   { ID id-TransactionID CRITICALITY reject TYPE TransactionID PRESENCE mandatory }|
   { ID id-RequestType CRITICALITY reject TYPE RequestType PRESENCE mandatory }|
   { ID id-EUTRA-NR-CellResourceCoordinationReq-Container CRITICALITY reject TYPE EUTRA-NR-CellResourceCoordinationReq-Container PRESENCE mandatory}|
   { ID id-IgnoreResourceCoordinationContainer CRITICALITY reject TYPE IgnoreResourceCoordinationContainer PRESENCE optional },
   ...
}

-- **************************************************************
--
-- GNB-DU RESOURCE COORDINATION RESPONSE
--
-- **************************************************************

GNBDUResourceCoordinationResponse ::= SEQUENCE {
   protocolIEs ProtocolIE-Container {{GNBDUResourceCoordinationResponse-IEs}},
   ...
}

GNBDUResourceCoordinationResponse-IEs F1AP-PROTOCOL-IES ::= {
   { ID id-TransactionID CRITICALITY reject TYPE TransactionID PRESENCE mandatory }|
   { ID id-EUTRA-NR-CellResourceCoordinationReqAck-Container CRITICALITY reject TYPE EUTRA-NR-CellResourceCoordinationReqAck-Container PRESENCE mandatory},
   ...
}

-- **************************************************************
--
-- UE Context Setup ELEMENTARY PROCEDURE
--
-- **************************************************************

-- **************************************************************
--
-- UE CONTEXT SETUP REQUEST
--
-- **************************************************************

UEContextSetupRequest ::= SEQUENCE {
   protocolIEs ProtocolIE-Container { { UEContextSetupRequestIEs} },
   ...
}

UEContextSetupRequestIEs F1AP-PROTOCOL-IES ::= {
   { ID id-gNB-CU-UE-F1AP-ID CRITICALITY reject TYPE GNB-CU-UE-F1AP-ID PRESENCE mandatory }|
   { ID id-gNB-DU-UE-F1AP-ID CRITICALITY ignore TYPE GNB-DU-UE-F1AP-ID PRESENCE optional }|
   { ID id-SpCell-ID CRITICALITY reject TYPE NRCGI PRESENCE mandatory }|
   { ID id-ServCellIndex CRITICALITY reject TYPE ServCellIndex PRESENCE mandatory }|
   { ID id-SpCellULConfigured CRITICALITY ignore TYPE CellULConfigured PRESENCE optional }|
   { ID id-CUtoDURRCInformation CRITICALITY reject TYPE CUtoDURRCInformation PRESENCE mandatory}|
   { ID id-Candidate-SpCell-List CRITICALITY ignore TYPE Candidate-SpCell-List PRESENCE optional }|
   { ID id-DRXCycle CRITICALITY ignore TYPE DRXCycle PRESENCE optional }|
   { ID id-ResourceCoordinationTransferContainer CRITICALITY ignore TYPE ResourceCoordinationTransferContainer PRESENCE optional }|
   { ID id-SCell-ToBeSetup-List CRITICALITY ignore TYPE SCell-ToBeSetup-List PRESENCE optional }|
   { ID id-SRBs-ToBeSetup-List CRITICALITY reject TYPE SRBs-ToBeSetup-List PRESENCE optional }|
   { ID id-DRBs-ToBeSetup-List CRITICALITY reject TYPE DRBs-ToBeSetup-List PRESENCE optional }|
   { ID id-InactivityMonitoringRequest CRITICALITY reject TYPE InactivityMonitoringRequest PRESENCE optional }|
   { ID id-RAT-FrequencyPriorityInformation CRITICALITY reject TYPE RAT-FrequencyPriorityInformation PRESENCE optional }|
   { ID id-RRCContainer CRITICALITY ignore TYPE RRCContainer PRESENCE optional }|
   { ID id-MaskedIMEISV CRITICALITY ignore TYPE MaskedIMEISV PRESENCE optional }|
   { ID id-ServingPLMN CRITICALITY ignore TYPE PLMN-Identity PRESENCE optional }|
   { ID id-GNB-DU-UE-AMBR-UL CRITICALITY ignore TYPE BitRate PRESENCE conditional }|
   { ID id-RRCDeliveryStatusRequest CRITICALITY ignore TYPE RRCDeliveryStatusRequest PRESENCE optional }|
   { ID id-ResourceCoordinationTransferInformation CRITICALITY ignore TYPE ResourceCoordinationTransferInformation PRESENCE optional }|
   { ID id-ServingCellMO CRITICALITY ignore TYPE ServingCellMO PRESENCE optional }|
   { ID id-new-gNB-CU-UE-F1AP-ID CRITICALITY reject TYPE GNB-DU-UE-F1AP-ID PRESENCE optional }|
   { ID id-RANUEID CRITICALITY ignore TYPE RANUEID PRESENCE optional }|
   { ID id-TraceActivation CRITICALITY ignore TYPE TraceActivation PRESENCE optional }|
   { ID id-AdditionalRRMPriorityIndex CRITICALITY ignore TYPE AdditionalRRMPriorityIndex PRESENCE optional }|
   { ID id-BHChannels-ToBeSetup-List CRITICALITY reject TYPE BHChannels-ToBeSetup-List PRESENCE optional }|
   { ID id-ConfiguredBAPAddress CRITICALITY reject TYPE BAPAddress PRESENCE optional }|
   { ID id-NRV2XServicesAuthorized CRITICALITY ignore TYPE NRV2XServicesAuthorized PRESENCE optional }|
   { ID id-LTEV2XServicesAuthorized CRITICALITY ignore TYPE LTEV2XServicesAuthorized PRESENCE optional }|
   { ID id-NRUESidelinkAggregateMaximumBitrate CRITICALITY ignore TYPE NRUESidelinkAggregateMaximumBitrate PRESENCE optional }|
   { ID id-LTEUESidelinkAggregateMaximumBitrate CRITICALITY ignore TYPE LTEUESidelinkAggregateMaximumBitrate PRESENCE optional }|
   { ID id-PC5LinkAMBR CRITICALITY ignore TYPE BitRate PRESENCE optional}|
   { ID id-SLDRBs-ToBeSetup-List CRITICALITY reject TYPE SLDRBs-ToBeSetup-List PRESENCE optional }|
   { ID id-ConditionalInterDUMobilityInformation CRITICALITY reject TYPE ConditionalInterDUMobilityInformation PRESENCE optional}|
   { ID id-ManagementBasedMDTPLMNList CRITICALITY ignore TYPE MDTPLMNList PRESENCE optional }|
   { ID id-ServingNID CRITICALITY reject TYPE NID PRESENCE optional }|
   { ID id-F1CTransferPath CRITICALITY reject TYPE F1CTransferPath PRESENCE optional },
   ...
}

Candidate-SpCell-List::= SEQUENCE (SIZE(1..maxnoofCandidateSpCells)) OF ProtocolIE-SingleContainer { { Candidate-SpCell-ItemIEs} }
SCell-ToBeSetup-List::= SEQUENCE (SIZE(1..maxnoofSCells)) OF ProtocolIE-SingleContainer { { SCell-ToBeSetup-ItemIEs} }
SRBs-ToBeSetup-List ::= SEQUENCE (SIZE(1..maxnoofSRBs)) OF ProtocolIE-SingleContainer { { SRBs-ToBeSetup-ItemIEs} }
DRBs-ToBeSetup-List ::= SEQUENCE (SIZE(1..maxnoofDRBs)) OF ProtocolIE-SingleContainer { { DRBs-ToBeSetup-ItemIEs} }
BHChannels-ToBeSetup-List ::= SEQUENCE (SIZE(1..maxnoofBHRLCChannels)) OF ProtocolIE-SingleContainer { { BHChannels-ToBeSetup-ItemIEs} }
SLDRBs-ToBeSetup-List ::= SEQUENCE (SIZE(1..maxnoofSLDRBs)) OF ProtocolIE-SingleContainer { { SLDRBs-ToBeSetup-ItemIEs} }

Candidate-SpCell-ItemIEs F1AP-PROTOCOL-IES ::= {
   { ID id-Candidate-SpCell-Item CRITICALITY ignore TYPE Candidate-SpCell-Item PRESENCE mandatory },
   ...
}

SCell-ToBeSetup-ItemIEs F1AP-PROTOCOL-IES ::= {
   { ID id-SCell-ToBeSetup-Item CRITICALITY ignore TYPE SCell-ToBeSetup-Item PRESENCE mandatory },
   ...
}

SRBs-ToBeSetup-ItemIEs F1AP-PROTOCOL-IES ::= {
   { ID id-SRBs-ToBeSetup-Item CRITICALITY reject TYPE SRBs-ToBeSetup-Item PRESENCE mandatory},
   ...
}

DRBs-ToBeSetup-ItemIEs F1AP-PROTOCOL-IES ::= {
   { ID id-DRBs-ToBeSetup-Item CRITICALITY reject TYPE DRBs-ToBeSetup-Item PRESENCE mandatory},
   ...
}

BHChannels-ToBeSetup-ItemIEs F1AP-PROTOCOL-IES ::= {
   { ID id-BHChannels-ToBeSetup-Item CRITICALITY reject TYPE BHChannels-ToBeSetup-Item PRESENCE mandatory},
   ...
}

SLDRBs-ToBeSetup-ItemIEs F1AP-PROTOCOL-IES ::= {
   { ID id-SLDRBs-ToBeSetup-Item CRITICALITY reject TYPE SLDRBs-ToBeSetup-Item PRESENCE mandatory},
   ...
}

-- **************************************************************
--
-- UE CONTEXT SETUP RESPONSE
--
-- **************************************************************

UEContextSetupResponse ::= SEQUENCE {
   protocolIEs ProtocolIE-Container { { UEContextSetupResponseIEs} },
   ...
}

UEContextSetupResponseIEs F1AP-PROTOCOL-IES ::= {
   { ID id-gNB-CU-UE-F1AP-ID CRITICALITY reject TYPE GNB-CU-UE-F1AP-ID PRESENCE mandatory }|
   { ID id-gNB-DU-UE-F1AP-ID CRITICALITY reject TYPE GNB-DU-UE-F1AP-ID PRESENCE mandatory }|
   { ID id-DUtoCURRCInformation CRITICALITY reject TYPE DUtoCURRCInformation PRESENCE mandatory }|
   { ID id-C-RNTI CRITICALITY ignore TYPE C-RNTI PRESENCE optional }|
   { ID id-ResourceCoordinationTransferContainer CRITICALITY ignore TYPE ResourceCoordinationTransferContainer PRESENCE optional }|
   { ID id-FullConfiguration CRITICALITY reject TYPE FullConfiguration PRESENCE optional }|
   { ID id-DRBs-Setup-List CRITICALITY ignore TYPE DRBs-Setup-List PRESENCE optional }|
   { ID id-SRBs-FailedToBeSetup-List CRITICALITY ignore TYPE SRBs-FailedToBeSetup-List PRESENCE optional }|
   { ID id-DRBs-FailedToBeSetup-List CRITICALITY ignore TYPE DRBs-FailedToBeSetup-List PRESENCE optional }|
   { ID id-SCell-FailedtoSetup-List CRITICALITY ignore TYPE SCell-FailedtoSetup-List PRESENCE optional }|
   { ID id-InactivityMonitoringResponse CRITICALITY reject TYPE InactivityMonitoringResponse PRESENCE optional }|
   { ID id-CriticalityDiagnostics CRITICALITY ignore TYPE CriticalityDiagnostics PRESENCE optional }|
   { ID id-SRBs-Setup-List CRITICALITY ignore TYPE SRBs-Setup-List PRESENCE optional }|
   { ID id-BHChannels-Setup-List CRITICALITY ignore TYPE BHChannels-Setup-List PRESENCE optional }|
   { ID id-BHChannels-FailedToBeSetup-List CRITICALITY ignore TYPE BHChannels-FailedToBeSetup-List PRESENCE optional }|
   { ID id-SLDRBs-Setup-List CRITICALITY ignore TYPE SLDRBs-Setup-List PRESENCE optional }|
   { ID id-SLDRBs-FailedToBeSetup-List CRITICALITY ignore TYPE SLDRBs-FailedToBeSetup-List PRESENCE optional }|
   { ID id-requestedTargetCellGlobalID CRITICALITY reject TYPE NRCGI PRESENCE optional},
   ...
}

DRBs-Setup-List ::= SEQUENCE (SIZE(1..maxnoofDRBs)) OF ProtocolIE-SingleContainer { { DRBs-Setup-ItemIEs} }

SRBs-FailedToBeSetup-List ::= SEQUENCE (SIZE(1..maxnoofSRBs)) OF ProtocolIE-SingleContainer { { SRBs-FailedToBeSetup-ItemIEs} }
DRBs-FailedToBeSetup-List ::= SEQUENCE (SIZE(1..maxnoofDRBs)) OF ProtocolIE-SingleContainer { { DRBs-FailedToBeSetup-ItemIEs} }
SCell-FailedtoSetup-List ::= SEQUENCE (SIZE(1..maxnoofSCells)) OF ProtocolIE-SingleContainer { { SCell-FailedtoSetup-ItemIEs} }
SRBs-Setup-List ::= SEQUENCE (SIZE(1..maxnoofSRBs)) OF ProtocolIE-SingleContainer { { SRBs-Setup-ItemIEs} }
BHChannels-Setup-List ::= SEQUENCE (SIZE(1..maxnoofBHRLCChannels)) OF ProtocolIE-SingleContainer { { BHChannels-Setup-ItemIEs} }
BHChannels-FailedToBeSetup-List ::= SEQUENCE (SIZE(1..maxnoofBHRLCChannels)) OF ProtocolIE-SingleContainer { { BHChannels-FailedToBeSetup-ItemIEs} }

DRBs-Setup-ItemIEs F1AP-PROTOCOL-IES ::= {
   { ID id-DRBs-Setup-Item CRITICALITY ignore TYPE DRBs-Setup-Item PRESENCE mandatory},
   ...
}

SRBs-Setup-ItemIEs F1AP-PROTOCOL-IES ::= {
   { ID id-SRBs-Setup-Item CRITICALITY ignore TYPE SRBs-Setup-Item PRESENCE mandatory},
   ...
}

SRBs-FailedToBeSetup-ItemIEs F1AP-PROTOCOL-IES ::= {
   { ID id-SRBs-FailedToBeSetup-Item CRITICALITY ignore TYPE SRBs-FailedToBeSetup-Item PRESENCE mandatory},
   ...
}

DRBs-FailedToBeSetup-ItemIEs F1AP-PROTOCOL-IES ::= {
   { ID id-DRBs-FailedToBeSetup-Item CRITICALITY ignore TYPE DRBs-FailedToBeSetup-Item PRESENCE mandatory},
   ...
}

SCell-FailedtoSetup-ItemIEs F1AP-PROTOCOL-IES ::= {
   { ID id-SCell-FailedtoSetup-Item CRITICALITY ignore TYPE SCell-FailedtoSetup-Item PRESENCE mandatory},
   ...
}

BHChannels-Setup-ItemIEs F1AP-PROTOCOL-IES ::= {
   { ID id-BHChannels-Setup-Item CRITICALITY ignore TYPE BHChannels-Setup-Item PRESENCE mandatory},
   ...
}

BHChannels-FailedToBeSetup-ItemIEs F1AP-PROTOCOL-IES ::= {
   { ID id-BHChannels-FailedToBeSetup-Item CRITICALITY ignore TYPE BHChannels-FailedToBeSetup-Item PRESENCE mandatory},
   ...
}

SLDRBs-Setup-List ::= SEQUENCE (SIZE(1..maxnoofSLDRBs)) OF ProtocolIE-SingleContainer { { SLDRBs-Setup-ItemIEs} }

SLDRBs-FailedToBeSetup-List ::= SEQUENCE (SIZE(1..maxnoofSLDRBs)) OF ProtocolIE-SingleContainer { { SLDRBs-FailedToBeSetup-ItemIEs} }

SLDRBs-Setup-ItemIEs F1AP-PROTOCOL-IES ::= {
   { ID id-SLDRBs-Setup-Item CRITICALITY ignore TYPE SLDRBs-Setup-Item PRESENCE mandatory},
   ...
}

SLDRBs-FailedToBeSetup-ItemIEs F1AP-PROTOCOL-IES ::= {
   { ID id-SLDRBs-FailedToBeSetup-Item CRITICALITY ignore TYPE SLDRBs-FailedToBeSetup-Item PRESENCE mandatory},
   ...
}

-- **************************************************************
--
-- UE CONTEXT SETUP FAILURE
--
-- **************************************************************

UEContextSetupFailure ::= SEQUENCE {
   protocolIEs ProtocolIE-Container { { UEContextSetupFailureIEs} },
   ...
}

UEContextSetupFailureIEs F1AP-PROTOCOL-IES ::= {
   { ID id-gNB-CU-UE-F1AP-ID CRITICALITY reject TYPE GNB-CU-UE-F1AP-ID PRESENCE mandatory }|
   { ID id-gNB-DU-UE-F1AP-ID CRITICALITY ignore TYPE GNB-DU-UE-F1AP-ID PRESENCE optional }|
   { ID id-Cause CRITICALITY ignore TYPE Cause PRESENCE mandatory }|
   { ID id-CriticalityDiagnostics CRITICALITY ignore TYPE CriticalityDiagnostics PRESENCE optional }|
   { ID id-Potential-SpCell-List CRITICALITY ignore TYPE Potential-SpCell-List PRESENCE optional }|
   { ID id-requestedTargetCellGlobalID CRITICALITY reject TYPE NRCGI PRESENCE optional},
   ...
}

Potential-SpCell-List::= SEQUENCE (SIZE(0..maxnoofPotentialSpCells)) OF ProtocolIE-SingleContainer { { Potential-SpCell-ItemIEs} }

Potential-SpCell-ItemIEs F1AP-PROTOCOL-IES ::= {
   { ID id-Potential-SpCell-Item CRITICALITY ignore TYPE Potential-SpCell-Item PRESENCE mandatory },
   ...
}

-- **************************************************************
--
-- UE Context Release Request ELEMENTARY PROCEDURE
--
-- **************************************************************

-- **************************************************************
--
-- UE Context Release Request
--
-- **************************************************************

UEContextReleaseRequest ::= SEQUENCE {
   protocolIEs ProtocolIE-Container {{ UEContextReleaseRequestIEs}},
   ...
}

UEContextReleaseRequestIEs F1AP-PROTOCOL-IES ::= {
   { ID id-gNB-CU-UE-F1AP-ID CRITICALITY reject TYPE GNB-CU-UE-F1AP-ID PRESENCE mandatory }|
   { ID id-gNB-DU-UE-F1AP-ID CRITICALITY reject TYPE GNB-DU-UE-F1AP-ID PRESENCE mandatory }|
   { ID id-Cause CRITICALITY ignore TYPE Cause PRESENCE mandatory }|
   { ID id-targetCellsToCancel CRITICALITY reject TYPE TargetCellList PRESENCE optional },
   ...
}

-- **************************************************************
--
-- UE Context Release (gNB-CU initiated) ELEMENTARY PROCEDURE
--
-- **************************************************************

-- **************************************************************
--
-- UE CONTEXT RELEASE COMMAND
--
-- **************************************************************

UEContextReleaseCommand ::= SEQUENCE {
   protocolIEs ProtocolIE-Container { { UEContextReleaseCommandIEs} },
   ...
}

UEContextReleaseCommandIEs F1AP-PROTOCOL-IES ::= {
   { ID id-gNB-CU-UE-F1AP-ID CRITICALITY reject TYPE GNB-CU-UE-F1AP-ID PRESENCE mandatory }|
   { ID id-gNB-DU-UE-F1AP-ID CRITICALITY reject TYPE GNB-DU-UE-F1AP-ID PRESENCE mandatory }|
   { ID id-Cause CRITICALITY ignore TYPE Cause PRESENCE mandatory }|
   { ID id-RRCContainer CRITICALITY ignore TYPE RRCContainer PRESENCE optional }|
   { ID id-SRBID CRITICALITY ignore TYPE SRBID PRESENCE conditional }|
   { ID id-oldgNB-DU-UE-F1AP-ID CRITICALITY ignore TYPE GNB-DU-UE-F1AP-ID PRESENCE optional }|
   { ID id-ExecuteDuplication CRITICALITY ignore TYPE ExecuteDuplication PRESENCE optional}|
   { ID id-RRCDeliveryStatusRequest CRITICALITY ignore TYPE RRCDeliveryStatusRequest PRESENCE optional }|
   { ID id-targetCellsToCancel CRITICALITY reject TYPE TargetCellList PRESENCE optional},
   ...
}

-- **************************************************************
--
-- UE CONTEXT RELEASE COMPLETE
--
-- **************************************************************

UEContextReleaseComplete ::= SEQUENCE {
   protocolIEs ProtocolIE-Container { { UEContextReleaseCompleteIEs} },
   ...
}

UEContextReleaseCompleteIEs F1AP-PROTOCOL-IES ::= {
   { ID id-gNB-CU-UE-F1AP-ID CRITICALITY reject TYPE GNB-CU-UE-F1AP-ID PRESENCE mandatory }|
   { ID id-gNB-DU-UE-F1AP-ID CRITICALITY reject TYPE GNB-DU-UE-F1AP-ID PRESENCE mandatory }|
   { ID id-CriticalityDiagnostics CRITICALITY ignore TYPE CriticalityDiagnostics PRESENCE optional },
   ...
}

-- **************************************************************
--
-- UE Context Modification ELEMENTARY PROCEDURE
--
-- **************************************************************

-- **************************************************************
--
-- UE CONTEXT MODIFICATION REQUEST
--
-- **************************************************************

UEContextModificationRequest ::= SEQUENCE {
   protocolIEs ProtocolIE-Container { { UEContextModificationRequestIEs} },
   ...
}

UEContextModificationRequestIEs F1AP-PROTOCOL-IES ::= {
   { ID id-gNB-CU-UE-F1AP-ID CRITICALITY reject TYPE GNB-CU-UE-F1AP-ID PRESENCE mandatory }|
   { ID id-gNB-DU-UE-F1AP-ID CRITICALITY reject TYPE GNB-DU-UE-F1AP-ID PRESENCE mandatory }|
   { ID id-SpCell-ID CRITICALITY ignore TYPE NRCGI PRESENCE optional }|
   { ID id-ServCellIndex CRITICALITY reject TYPE ServCellIndex PRESENCE optional }|
   { ID id-SpCellULConfigured CRITICALITY ignore TYPE CellULConfigured PRESENCE optional }|
   { ID id-DRXCycle CRITICALITY ignore TYPE DRXCycle PRESENCE optional }|
   { ID id-CUtoDURRCInformation CRITICALITY reject TYPE CUtoDURRCInformation PRESENCE optional }|
   { ID id-TransmissionActionIndicator CRITICALITY ignore TYPE TransmissionActionIndicator PRESENCE optional }|
   { ID id-ResourceCoordinationTransferContainer CRITICALITY ignore TYPE ResourceCoordinationTransferContainer PRESENCE optional }|
   { ID id-RRCReconfigurationCompleteIndicator CRITICALITY ignore TYPE RRCReconfigurationCompleteIndicator PRESENCE optional }|
   { ID id-RRCContainer CRITICALITY reject TYPE RRCContainer PRESENCE optional }|
   { ID id-SCell-ToBeSetupMod-List CRITICALITY ignore TYPE SCell-ToBeSetupMod-List PRESENCE optional }|
   { ID id-SCell-ToBeRemoved-List CRITICALITY ignore TYPE SCell-ToBeRemoved-List PRESENCE optional }|
   { ID id-SRBs-ToBeSetupMod-List CRITICALITY reject TYPE SRBs-ToBeSetupMod-List PRESENCE optional }|
   { ID id-DRBs-ToBeSetupMod-List CRITICALITY reject TYPE DRBs-ToBeSetupMod-List PRESENCE optional }|
   { ID id-DRBs-ToBeModified-List CRITICALITY reject TYPE DRBs-ToBeModified-List PRESENCE optional }|
   { ID id-SRBs-ToBeReleased-List CRITICALITY reject TYPE SRBs-ToBeReleased-List PRESENCE optional }|
   { ID id-DRBs-ToBeReleased-List CRITICALITY reject TYPE DRBs-ToBeReleased-List PRESENCE optional }|
   { ID id-InactivityMonitoringRequest CRITICALITY reject TYPE InactivityMonitoringRequest PRESENCE optional }|
   { ID id-RAT-FrequencyPriorityInformation CRITICALITY reject TYPE RAT-FrequencyPriorityInformation PRESENCE optional }|
   { ID id-DRXConfigurationIndicator CRITICALITY ignore TYPE DRXConfigurationIndicator PRESENCE optional }|
   { ID id-RLCFailureIndication CRITICALITY ignore TYPE RLCFailureIndication PRESENCE optional }|
   { ID id-UplinkTxDirectCurrentListInformation CRITICALITY ignore TYPE UplinkTxDirectCurrentListInformation PRESENCE optional }|
   { ID id-GNB-DUConfigurationQuery CRITICALITY reject TYPE GNB-DUConfigurationQuery PRESENCE optional }|
   { ID id-GNB-DU-UE-AMBR-UL CRITICALITY ignore TYPE BitRate PRESENCE optional }|
   { ID id-ExecuteDuplication CRITICALITY ignore TYPE ExecuteDuplication PRESENCE optional}|
   { ID id-RRCDeliveryStatusRequest CRITICALITY ignore TYPE RRCDeliveryStatusRequest PRESENCE optional }|
   { ID id-ResourceCoordinationTransferInformation CRITICALITY ignore TYPE ResourceCoordinationTransferInformation PRESENCE optional }|
   { ID id-ServingCellMO CRITICALITY ignore TYPE ServingCellMO PRESENCE optional }|
   { ID id-NeedforGap CRITICALITY ignore TYPE NeedforGap PRESENCE optional }|
   { ID id-FullConfiguration CRITICALITY reject TYPE FullConfiguration PRESENCE optional }|
   { ID id-AdditionalRRMPriorityIndex CRITICALITY ignore TYPE AdditionalRRMPriorityIndex PRESENCE optional }|
   { ID id-LowerLayerPresenceStatusChange CRITICALITY ignore TYPE LowerLayerPresenceStatusChange PRESENCE optional }|
   { ID id-BHChannels-ToBeSetupMod-List CRITICALITY reject TYPE BHChannels-ToBeSetupMod-List PRESENCE optional }|
   { ID id-BHChannels-ToBeModified-List CRITICALITY reject TYPE BHChannels-ToBeModified-List PRESENCE optional }|
   { ID id-BHChannels-ToBeReleased-List CRITICALITY reject TYPE BHChannels-ToBeReleased-List PRESENCE optional }|
   { ID id-NRV2XServicesAuthorized CRITICALITY ignore TYPE NRV2XServicesAuthorized PRESENCE optional }|
   { ID id-LTEV2XServicesAuthorized CRITICALITY ignore TYPE LTEV2XServicesAuthorized PRESENCE optional }|
   { ID id-NRUESidelinkAggregateMaximumBitrate CRITICALITY ignore TYPE NRUESidelinkAggregateMaximumBitrate PRESENCE optional }|
   { ID id-LTEUESidelinkAggregateMaximumBitrate CRITICALITY ignore TYPE LTEUESidelinkAggregateMaximumBitrate PRESENCE optional }|
   { ID id-PC5LinkAMBR CRITICALITY ignore TYPE BitRate PRESENCE optional}|
   { ID id-SLDRBs-ToBeSetupMod-List CRITICALITY reject TYPE SLDRBs-ToBeSetupMod-List PRESENCE optional }|
   { ID id-SLDRBs-ToBeModified-List CRITICALITY reject TYPE SLDRBs-ToBeModified-List PRESENCE optional }|
   { ID id-SLDRBs-ToBeReleased-List CRITICALITY reject TYPE SLDRBs-ToBeReleased-List PRESENCE optional }|
   { ID id-ConditionalIntraDUMobilityInformation CRITICALITY reject TYPE ConditionalIntraDUMobilityInformation PRESENCE optional}|
   { ID id-F1CTransferPath CRITICALITY reject TYPE F1CTransferPath PRESENCE optional }|
   { ID id-SCGIndicator CRITICALITY ignore TYPE SCGIndicator PRESENCE optional },
   ...
}

SCell-ToBeSetupMod-List::= SEQUENCE (SIZE(1..maxnoofSCells)) OF ProtocolIE-SingleContainer { { SCell-ToBeSetupMod-ItemIEs} }
SCell-ToBeRemoved-List::= SEQUENCE (SIZE(1..maxnoofSCells)) OF ProtocolIE-SingleContainer { { SCell-ToBeRemoved-ItemIEs} }
SRBs-ToBeSetupMod-List ::= SEQUENCE (SIZE(1..maxnoofSRBs)) OF ProtocolIE-SingleContainer { { SRBs-ToBeSetupMod-ItemIEs} }
DRBs-ToBeSetupMod-List ::= SEQUENCE (SIZE(1..maxnoofDRBs)) OF ProtocolIE-SingleContainer { { DRBs-ToBeSetupMod-ItemIEs} }
BHChannels-ToBeSetupMod-List ::= SEQUENCE (SIZE(1..maxnoofBHRLCChannels)) OF ProtocolIE-SingleContainer { { BHChannels-ToBeSetupMod-ItemIEs} }

DRBs-ToBeModified-List ::= SEQUENCE (SIZE(1..maxnoofDRBs)) OF ProtocolIE-SingleContainer { { DRBs-ToBeModified-ItemIEs} }
BHChannels-ToBeModified-List ::= SEQUENCE (SIZE(1..maxnoofBHRLCChannels)) OF ProtocolIE-SingleContainer { { BHChannels-ToBeModified-ItemIEs} }
SRBs-ToBeReleased-List ::= SEQUENCE (SIZE(1..maxnoofSRBs)) OF ProtocolIE-SingleContainer { { SRBs-ToBeReleased-ItemIEs} }
DRBs-ToBeReleased-List ::= SEQUENCE (SIZE(1..maxnoofDRBs)) OF ProtocolIE-SingleContainer { { DRBs-ToBeReleased-ItemIEs} }
BHChannels-ToBeReleased-List ::= SEQUENCE (SIZE(1..maxnoofBHRLCChannels)) OF ProtocolIE-SingleContainer { { BHChannels-ToBeReleased-ItemIEs} }

SCell-ToBeSetupMod-ItemIEs F1AP-PROTOCOL-IES ::= {
   { ID id-SCell-ToBeSetupMod-Item CRITICALITY ignore TYPE SCell-ToBeSetupMod-Item PRESENCE mandatory },
   ...
}

SCell-ToBeRemoved-ItemIEs F1AP-PROTOCOL-IES ::= {
   { ID id-SCell-ToBeRemoved-Item CRITICALITY ignore TYPE SCell-ToBeRemoved-Item PRESENCE mandatory },
   ...
}

SRBs-ToBeSetupMod-ItemIEs F1AP-PROTOCOL-IES ::= {
   { ID id-SRBs-ToBeSetupMod-Item CRITICALITY reject TYPE SRBs-ToBeSetupMod-Item PRESENCE mandatory},
   ...
}

DRBs-ToBeSetupMod-ItemIEs F1AP-PROTOCOL-IES ::= {
   { ID id-DRBs-ToBeSetupMod-Item CRITICALITY reject TYPE DRBs-ToBeSetupMod-Item PRESENCE mandatory},
   ...
}

DRBs-ToBeModified-ItemIEs F1AP-PROTOCOL-IES ::= {
   { ID id-DRBs-ToBeModified-Item CRITICALITY reject TYPE DRBs-ToBeModified-Item PRESENCE mandatory},
   ...
}

SRBs-ToBeReleased-ItemIEs F1AP-PROTOCOL-IES ::= {
   { ID id-SRBs-ToBeReleased-Item CRITICALITY reject TYPE SRBs-ToBeReleased-Item PRESENCE mandatory},
   ...
}

DRBs-ToBeReleased-ItemIEs F1AP-PROTOCOL-IES ::= {
   { ID id-DRBs-ToBeReleased-Item CRITICALITY reject TYPE DRBs-ToBeReleased-Item PRESENCE mandatory},
   ...
}

BHChannels-ToBeSetupMod-ItemIEs F1AP-PROTOCOL-IES ::= {
   { ID id-BHChannels-ToBeSetupMod-Item CRITICALITY reject TYPE BHChannels-ToBeSetupMod-Item PRESENCE mandatory},
   ...
}

BHChannels-ToBeModified-ItemIEs F1AP-PROTOCOL-IES ::= {
   { ID id-BHChannels-ToBeModified-Item CRITICALITY reject TYPE BHChannels-ToBeModified-Item PRESENCE mandatory},
   ...
}

BHChannels-ToBeReleased-ItemIEs F1AP-PROTOCOL-IES ::= {
   { ID id-BHChannels-ToBeReleased-Item CRITICALITY reject TYPE BHChannels-ToBeReleased-Item PRESENCE mandatory},
   ...
}

SLDRBs-ToBeSetupMod-List ::= SEQUENCE (SIZE(1..maxnoofSLDRBs)) OF ProtocolIE-SingleContainer { { SLDRBs-ToBeSetupMod-ItemIEs} }
SLDRBs-ToBeModified-List ::= SEQUENCE (SIZE(1..maxnoofSLDRBs)) OF ProtocolIE-SingleContainer { { SLDRBs-ToBeModified-ItemIEs} }
SLDRBs-ToBeReleased-List ::= SEQUENCE (SIZE(1..maxnoofSLDRBs)) OF ProtocolIE-SingleContainer { { SLDRBs-ToBeReleased-ItemIEs} }

SLDRBs-ToBeSetupMod-ItemIEs F1AP-PROTOCOL-IES ::= {
   { ID id-SLDRBs-ToBeSetupMod-Item CRITICALITY reject TYPE SLDRBs-ToBeSetupMod-Item PRESENCE mandatory},
   ...
}

SLDRBs-ToBeModified-ItemIEs F1AP-PROTOCOL-IES ::= {
   { ID id-SLDRBs-ToBeModified-Item CRITICALITY reject TYPE SLDRBs-ToBeModified-Item PRESENCE mandatory},
   ...
}

SLDRBs-ToBeReleased-ItemIEs F1AP-PROTOCOL-IES ::= {
   { ID id-SLDRBs-ToBeReleased-Item CRITICALITY reject TYPE SLDRBs-ToBeReleased-Item PRESENCE mandatory},
   ...
}

-- **************************************************************
--
-- UE CONTEXT MODIFICATION RESPONSE
--
-- **************************************************************

UEContextModificationResponse ::= SEQUENCE {
   protocolIEs ProtocolIE-Container { { UEContextModificationResponseIEs} },
   ...
}

UEContextModificationResponseIEs F1AP-PROTOCOL-IES ::= {
   { ID id-gNB-CU-UE-F1AP-ID CRITICALITY reject TYPE GNB-CU-UE-F1AP-ID PRESENCE mandatory }|
   { ID id-gNB-DU-UE-F1AP-ID CRITICALITY reject TYPE GNB-DU-UE-F1AP-ID PRESENCE mandatory }|
   { ID id-ResourceCoordinationTransferContainer CRITICALITY ignore TYPE ResourceCoordinationTransferContainer PRESENCE optional }|
   { ID id-DUtoCURRCInformation CRITICALITY reject TYPE DUtoCURRCInformation PRESENCE optional}|
   { ID id-DRBs-SetupMod-List CRITICALITY ignore TYPE DRBs-SetupMod-List PRESENCE optional}|
   { ID id-DRBs-Modified-List CRITICALITY ignore TYPE DRBs-Modified-List PRESENCE optional}|
   { ID id-SRBs-FailedToBeSetupMod-List CRITICALITY ignore TYPE SRBs-FailedToBeSetupMod-List PRESENCE optional }|
   { ID id-DRBs-FailedToBeSetupMod-List CRITICALITY ignore TYPE DRBs-FailedToBeSetupMod-List PRESENCE optional }|
   { ID id-SCell-FailedtoSetupMod-List CRITICALITY ignore TYPE SCell-FailedtoSetupMod-List PRESENCE optional }|
   { ID id-DRBs-FailedToBeModified-List CRITICALITY ignore TYPE DRBs-FailedToBeModified-List PRESENCE optional }|
   { ID id-InactivityMonitoringResponse CRITICALITY reject TYPE InactivityMonitoringResponse PRESENCE optional }|
   { ID id-CriticalityDiagnostics CRITICALITY ignore TYPE CriticalityDiagnostics PRESENCE optional }|
   { ID id-C-RNTI CRITICALITY ignore TYPE C-RNTI PRESENCE optional }|
   { ID id-Associated-SCell-List CRITICALITY ignore TYPE Associated-SCell-List PRESENCE optional }|
   { ID id-SRBs-SetupMod-List CRITICALITY ignore TYPE SRBs-SetupMod-List PRESENCE optional }|
   { ID id-SRBs-Modified-List CRITICALITY ignore TYPE SRBs-Modified-List PRESENCE optional }|
   { ID id-FullConfiguration CRITICALITY reject TYPE FullConfiguration PRESENCE optional }|
   { ID id-BHChannels-SetupMod-List CRITICALITY ignore TYPE BHChannels-SetupMod-List PRESENCE optional}|
   { ID id-BHChannels-Modified-List CRITICALITY ignore TYPE BHChannels-Modified-List PRESENCE optional}|
   { ID id-BHChannels-FailedToBeSetupMod-List CRITICALITY ignore TYPE BHChannels-FailedToBeSetupMod-List PRESENCE optional }|
   { ID id-BHChannels-FailedToBeModified-List CRITICALITY ignore TYPE BHChannels-FailedToBeModified-List PRESENCE optional }|
   { ID id-SLDRBs-SetupMod-List CRITICALITY ignore TYPE SLDRBs-SetupMod-List PRESENCE optional }|
   { ID id-SLDRBs-Modified-List CRITICALITY ignore TYPE SLDRBs-Modified-List PRESENCE optional }|
   { ID id-SLDRBs-FailedToBeSetupMod-List CRITICALITY ignore TYPE SLDRBs-FailedToBeSetupMod-List PRESENCE optional }|
   { ID id-SLDRBs-FailedToBeModified-List CRITICALITY ignore TYPE SLDRBs-FailedToBeModified-List PRESENCE optional }|
   { ID id-requestedTargetCellGlobalID CRITICALITY reject TYPE NRCGI PRESENCE optional},
   ...
}

DRBs-SetupMod-List ::= SEQUENCE (SIZE(1..maxnoofDRBs)) OF ProtocolIE-SingleContainer { { DRBs-SetupMod-ItemIEs} }
DRBs-Modified-List::= SEQUENCE (SIZE(1..maxnoofDRBs)) OF ProtocolIE-SingleContainer { { DRBs-Modified-ItemIEs } }
SRBs-SetupMod-List ::= SEQUENCE (SIZE(1..maxnoofSRBs)) OF ProtocolIE-SingleContainer { { SRBs-SetupMod-ItemIEs} }
SRBs-Modified-List ::= SEQUENCE (SIZE(1..maxnoofSRBs)) OF ProtocolIE-SingleContainer { { SRBs-Modified-ItemIEs } }
DRBs-FailedToBeModified-List ::= SEQUENCE (SIZE(1..maxnoofDRBs)) OF ProtocolIE-SingleContainer { { DRBs-FailedToBeModified-ItemIEs} }
SRBs-FailedToBeSetupMod-List ::= SEQUENCE (SIZE(1..maxnoofSRBs)) OF ProtocolIE-SingleContainer { { SRBs-FailedToBeSetupMod-ItemIEs} }
DRBs-FailedToBeSetupMod-List ::= SEQUENCE (SIZE(1..maxnoofDRBs)) OF ProtocolIE-SingleContainer { { DRBs-FailedToBeSetupMod-ItemIEs} }
SCell-FailedtoSetupMod-List ::= SEQUENCE (SIZE(1..maxnoofSCells)) OF ProtocolIE-SingleContainer { { SCell-FailedtoSetupMod-ItemIEs} }
BHChannels-SetupMod-List ::= SEQUENCE (SIZE(1..maxnoofBHRLCChannels)) OF ProtocolIE-SingleContainer { { BHChannels-SetupMod-ItemIEs} }
BHChannels-Modified-List ::= SEQUENCE (SIZE(1..maxnoofBHRLCChannels)) OF ProtocolIE-SingleContainer { { BHChannels-Modified-ItemIEs } }
BHChannels-FailedToBeModified-List ::= SEQUENCE (SIZE(1..maxnoofBHRLCChannels)) OF ProtocolIE-SingleContainer { { BHChannels-FailedToBeModified-ItemIEs} }
BHChannels-FailedToBeSetupMod-List ::= SEQUENCE (SIZE(1..maxnoofBHRLCChannels)) OF ProtocolIE-SingleContainer { { BHChannels-FailedToBeSetupMod-ItemIEs} }

Associated-SCell-List ::= SEQUENCE (SIZE(1.. maxnoofSCells)) OF ProtocolIE-SingleContainer { { Associated-SCell-ItemIEs} }

DRBs-SetupMod-ItemIEs F1AP-PROTOCOL-IES ::= {
   { ID id-DRBs-SetupMod-Item CRITICALITY ignore TYPE DRBs-SetupMod-Item PRESENCE mandatory},
   ...
}

DRBs-Modified-ItemIEs F1AP-PROTOCOL-IES ::= {
   { ID id-DRBs-Modified-Item CRITICALITY ignore TYPE DRBs-Modified-Item PRESENCE mandatory},
   ...
}

SRBs-SetupMod-ItemIEs F1AP-PROTOCOL-IES ::= {
   { ID id-SRBs-SetupMod-Item CRITICALITY ignore TYPE SRBs-SetupMod-Item PRESENCE mandatory},
   ...
}

SRBs-Modified-ItemIEs F1AP-PROTOCOL-IES ::= {
   { ID id-SRBs-Modified-Item CRITICALITY ignore TYPE SRBs-Modified-Item PRESENCE mandatory},
   ...
}

SRBs-FailedToBeSetupMod-ItemIEs F1AP-PROTOCOL-IES ::= {
   { ID id-SRBs-FailedToBeSetupMod-Item CRITICALITY ignore TYPE SRBs-FailedToBeSetupMod-Item PRESENCE mandatory},
   ...
}

DRBs-FailedToBeSetupMod-ItemIEs F1AP-PROTOCOL-IES ::= {
   { ID id-DRBs-FailedToBeSetupMod-Item CRITICALITY ignore TYPE DRBs-FailedToBeSetupMod-Item PRESENCE mandatory},
   ...
}

DRBs-FailedToBeModified-ItemIEs F1AP-PROTOCOL-IES ::= {
   { ID id-DRBs-FailedToBeModified-Item CRITICALITY ignore TYPE DRBs-FailedToBeModified-Item PRESENCE mandatory},
   ...
}

SCell-FailedtoSetupMod-ItemIEs F1AP-PROTOCOL-IES ::= {
   { ID id-SCell-FailedtoSetupMod-Item CRITICALITY ignore TYPE SCell-FailedtoSetupMod-Item PRESENCE mandatory},
   ...
}

Associated-SCell-ItemIEs F1AP-PROTOCOL-IES ::= {
   { ID id-Associated-SCell-Item CRITICALITY ignore TYPE Associated-SCell-Item PRESENCE mandatory},
   ...
}

BHChannels-SetupMod-ItemIEs F1AP-PROTOCOL-IES ::= {
   { ID id-BHChannels-SetupMod-Item CRITICALITY ignore TYPE BHChannels-SetupMod-Item PRESENCE mandatory},
   ...
}

BHChannels-Modified-ItemIEs F1AP-PROTOCOL-IES ::= {
   { ID id-BHChannels-Modified-Item CRITICALITY ignore TYPE BHChannels-Modified-Item PRESENCE mandatory},
   ...
}

BHChannels-FailedToBeSetupMod-ItemIEs F1AP-PROTOCOL-IES ::= {
   { ID id-BHChannels-FailedToBeSetupMod-Item CRITICALITY ignore TYPE BHChannels-FailedToBeSetupMod-Item PRESENCE mandatory},
   ...
}

BHChannels-FailedToBeModified-ItemIEs F1AP-PROTOCOL-IES ::= {
   { ID id-BHChannels-FailedToBeModified-Item CRITICALITY ignore TYPE BHChannels-FailedToBeModified-Item PRESENCE mandatory},
   ...
}

SLDRBs-SetupMod-List ::= SEQUENCE (SIZE(1..maxnoofSLDRBs)) OF ProtocolIE-SingleContainer { { SLDRBs-SetupMod-ItemIEs} }
SLDRBs-Modified-List ::= SEQUENCE (SIZE(1..maxnoofSLDRBs)) OF ProtocolIE-SingleContainer { { SLDRBs-Modified-ItemIEs } }
SLDRBs-FailedToBeModified-List ::= SEQUENCE (SIZE(1..maxnoofSLDRBs)) OF ProtocolIE-SingleContainer { { SLDRBs-FailedToBeModified-ItemIEs} }
SLDRBs-FailedToBeSetupMod-List ::= SEQUENCE (SIZE(1..maxnoofSLDRBs)) OF ProtocolIE-SingleContainer { { SLDRBs-FailedToBeSetupMod-ItemIEs} }

SLDRBs-SetupMod-ItemIEs F1AP-PROTOCOL-IES ::= {
   { ID id-SLDRBs-SetupMod-Item CRITICALITY ignore TYPE SLDRBs-SetupMod-Item PRESENCE mandatory},
   ...
}

SLDRBs-Modified-ItemIEs F1AP-PROTOCOL-IES ::= {
   { ID id-SLDRBs-Modified-Item CRITICALITY ignore TYPE SLDRBs-Modified-Item PRESENCE mandatory},
   ...
}

SLDRBs-FailedToBeSetupMod-ItemIEs F1AP-PROTOCOL-IES ::= {
   { ID id-SLDRBs-FailedToBeSetupMod-Item CRITICALITY ignore TYPE SLDRBs-FailedToBeSetupMod-Item PRESENCE mandatory},
   ...
}

SLDRBs-FailedToBeModified-ItemIEs F1AP-PROTOCOL-IES ::= {
   { ID id-SLDRBs-FailedToBeModified-Item CRITICALITY ignore TYPE SLDRBs-FailedToBeModified-Item PRESENCE mandatory},
   ...
}

-- **************************************************************
--
-- UE CONTEXT MODIFICATION FAILURE
--
-- **************************************************************

UEContextModificationFailure ::= SEQUENCE {
   protocolIEs ProtocolIE-Container { { UEContextModificationFailureIEs} },
   ...
}

UEContextModificationFailureIEs F1AP-PROTOCOL-IES ::= {
   { ID id-gNB-CU-UE-F1AP-ID CRITICALITY reject TYPE GNB-CU-UE-F1AP-ID PRESENCE mandatory }|
   { ID id-gNB-DU-UE-F1AP-ID CRITICALITY reject TYPE GNB-DU-UE-F1AP-ID PRESENCE mandatory }|
   { ID id-Cause CRITICALITY ignore TYPE Cause PRESENCE mandatory }|
   { ID id-CriticalityDiagnostics CRITICALITY ignore TYPE CriticalityDiagnostics PRESENCE optional }|
   { ID id-requestedTargetCellGlobalID CRITICALITY reject TYPE NRCGI PRESENCE optional},
   ...
}

-- **************************************************************
--
-- UE Context Modification Required (gNB-DU initiated) ELEMENTARY PROCEDURE
--
-- **************************************************************

-- **************************************************************
--
-- UE CONTEXT MODIFICATION REQUIRED
--
-- **************************************************************

UEContextModificationRequired ::= SEQUENCE {
   protocolIEs ProtocolIE-Container { { UEContextModificationRequiredIEs} },
   ...
}

UEContextModificationRequiredIEs F1AP-PROTOCOL-IES ::= {
   { ID id-gNB-CU-UE-F1AP-ID CRITICALITY reject TYPE GNB-CU-UE-F1AP-ID PRESENCE mandatory }|
   { ID id-gNB-DU-UE-F1AP-ID CRITICALITY reject TYPE GNB-DU-UE-F1AP-ID PRESENCE mandatory }|
   { ID id-ResourceCoordinationTransferContainer CRITICALITY ignore TYPE ResourceCoordinationTransferContainer PRESENCE optional }|
   { ID id-DUtoCURRCInformation CRITICALITY reject TYPE DUtoCURRCInformation PRESENCE optional}|
   { ID id-DRBs-Required-ToBeModified-List CRITICALITY reject TYPE DRBs-Required-ToBeModified-List PRESENCE optional}|
   { ID id-SRBs-Required-ToBeReleased-List CRITICALITY reject TYPE SRBs-Required-ToBeReleased-List PRESENCE optional}|
   { ID id-DRBs-Required-ToBeReleased-List CRITICALITY reject TYPE DRBs-Required-ToBeReleased-List PRESENCE optional}|
   { ID id-Cause CRITICALITY ignore TYPE Cause PRESENCE mandatory }|
   { ID id-BHChannels-Required-ToBeReleased-List CRITICALITY reject TYPE BHChannels-Required-ToBeReleased-List PRESENCE optional}|
   { ID id-SLDRBs-Required-ToBeModified-List CRITICALITY reject TYPE SLDRBs-Required-ToBeModified-List PRESENCE optional}|
   { ID id-SLDRBs-Required-ToBeReleased-List CRITICALITY reject TYPE SLDRBs-Required-ToBeReleased-List PRESENCE optional}|
   { ID id-targetCellsToCancel CRITICALITY reject TYPE TargetCellList PRESENCE optional},
   ...
}

DRBs-Required-ToBeModified-List::= SEQUENCE (SIZE(1..maxnoofDRBs)) OF ProtocolIE-SingleContainer { { DRBs-Required-ToBeModified-ItemIEs } }
DRBs-Required-ToBeReleased-List::= SEQUENCE (SIZE(1..maxnoofDRBs)) OF ProtocolIE-SingleContainer { { DRBs-Required-ToBeReleased-ItemIEs } }

SRBs-Required-ToBeReleased-List::= SEQUENCE (SIZE(1..maxnoofSRBs)) OF ProtocolIE-SingleContainer { { SRBs-Required-ToBeReleased-ItemIEs } }

BHChannels-Required-ToBeReleased-List ::= SEQUENCE (SIZE(1..maxnoofBHRLCChannels)) OF ProtocolIE-SingleContainer { { BHChannels-Required-ToBeReleased-ItemIEs } }

DRBs-Required-ToBeModified-ItemIEs F1AP-PROTOCOL-IES ::= {
   { ID id-DRBs-Required-ToBeModified-Item CRITICALITY reject TYPE DRBs-Required-ToBeModified-Item PRESENCE mandatory},
   ...
}

DRBs-Required-ToBeReleased-ItemIEs F1AP-PROTOCOL-IES ::= {
   { ID id-DRBs-Required-ToBeReleased-Item CRITICALITY reject TYPE DRBs-Required-ToBeReleased-Item PRESENCE mandatory},
   ...
}

SRBs-Required-ToBeReleased-ItemIEs F1AP-PROTOCOL-IES ::= {
   { ID id-SRBs-Required-ToBeReleased-Item CRITICALITY reject TYPE SRBs-Required-ToBeReleased-Item PRESENCE mandatory},
   ...
}

BHChannels-Required-ToBeReleased-ItemIEs F1AP-PROTOCOL-IES ::= {
   { ID id-BHChannels-Required-ToBeReleased-Item CRITICALITY reject TYPE BHChannels-Required-ToBeReleased-Item PRESENCE mandatory},
   ...
}

SLDRBs-Required-ToBeModified-List::= SEQUENCE (SIZE(1..maxnoofSLDRBs)) OF ProtocolIE-SingleContainer { { SLDRBs-Required-ToBeModified-ItemIEs } }
SLDRBs-Required-ToBeReleased-List::= SEQUENCE (SIZE(1..maxnoofSLDRBs)) OF ProtocolIE-SingleContainer { { SLDRBs-Required-ToBeReleased-ItemIEs } }

SLDRBs-Required-ToBeModified-ItemIEs F1AP-PROTOCOL-IES ::= {
   { ID id-SLDRBs-Required-ToBeModified-Item CRITICALITY reject TYPE SLDRBs-Required-ToBeModified-Item PRESENCE mandatory},
   ...
}

SLDRBs-Required-ToBeReleased-ItemIEs F1AP-PROTOCOL-IES ::= {
   { ID id-SLDRBs-Required-ToBeReleased-Item CRITICALITY reject TYPE SLDRBs-Required-ToBeReleased-Item PRESENCE mandatory},
   ...
}

-- **************************************************************
--
-- UE CONTEXT MODIFICATION CONFIRM
--
-- **************************************************************

UEContextModificationConfirm::= SEQUENCE {
   protocolIEs ProtocolIE-Container { { UEContextModificationConfirmIEs} },
   ...
}

UEContextModificationConfirmIEs F1AP-PROTOCOL-IES ::= {
   { ID id-gNB-CU-UE-F1AP-ID CRITICALITY reject TYPE GNB-CU-UE-F1AP-ID PRESENCE mandatory }|
   { ID id-gNB-DU-UE-F1AP-ID CRITICALITY reject TYPE GNB-DU-UE-F1AP-ID PRESENCE mandatory }|
   { ID id-ResourceCoordinationTransferContainer CRITICALITY ignore TYPE ResourceCoordinationTransferContainer PRESENCE optional }|
   { ID id-DRBs-ModifiedConf-List CRITICALITY ignore TYPE DRBs-ModifiedConf-List PRESENCE optional}|
   { ID id-RRCContainer CRITICALITY ignore TYPE RRCContainer PRESENCE optional }|
   { ID id-CriticalityDiagnostics CRITICALITY ignore TYPE CriticalityDiagnostics PRESENCE optional }|
   { ID id-ExecuteDuplication CRITICALITY ignore TYPE ExecuteDuplication PRESENCE optional}|
   { ID id-ResourceCoordinationTransferInformation CRITICALITY ignore TYPE ResourceCoordinationTransferInformation PRESENCE optional }|
   { ID id-SLDRBs-ModifiedConf-List CRITICALITY ignore TYPE SLDRBs-ModifiedConf-List PRESENCE optional},
   ...
}

DRBs-ModifiedConf-List::= SEQUENCE (SIZE(1..maxnoofDRBs)) OF ProtocolIE-SingleContainer { { DRBs-ModifiedConf-ItemIEs } }

DRBs-ModifiedConf-ItemIEs F1AP-PROTOCOL-IES ::= {
   { ID id-DRBs-ModifiedConf-Item CRITICALITY ignore TYPE DRBs-ModifiedConf-Item PRESENCE mandatory},
   ...
}

SLDRBs-ModifiedConf-List::= SEQUENCE (SIZE(1..maxnoofSLDRBs)) OF ProtocolIE-SingleContainer { { SLDRBs-ModifiedConf-ItemIEs } }

SLDRBs-ModifiedConf-ItemIEs F1AP-PROTOCOL-IES ::= {
   { ID id-SLDRBs-ModifiedConf-Item CRITICALITY ignore TYPE SLDRBs-ModifiedConf-Item PRESENCE mandatory},
   ...
}

-- **************************************************************
--
-- UE CONTEXT MODIFICATION REFUSE
--
-- **************************************************************

UEContextModificationRefuse::= SEQUENCE {
   protocolIEs ProtocolIE-Container { { UEContextModificationRefuseIEs} },
   ...
}

UEContextModificationRefuseIEs F1AP-PROTOCOL-IES ::= {
   { ID id-gNB-CU-UE-F1AP-ID CRITICALITY reject TYPE GNB-CU-UE-F1AP-ID PRESENCE mandatory }|
   { ID id-gNB-DU-UE-F1AP-ID CRITICALITY reject TYPE GNB-DU-UE-F1AP-ID PRESENCE mandatory }|
   { ID id-Cause CRITICALITY ignore TYPE Cause PRESENCE mandatory }|
   { ID id-CriticalityDiagnostics CRITICALITY ignore TYPE CriticalityDiagnostics PRESENCE optional },
   ...
}

-- **************************************************************
--
-- WRITE-REPLACE WARNING ELEMENTARY PROCEDURE
--
-- **************************************************************

-- **************************************************************
--
-- Write-Replace Warning Request
--
-- **************************************************************

WriteReplaceWarningRequest ::= SEQUENCE {
   protocolIEs ProtocolIE-Container { {WriteReplaceWarningRequestIEs} },
   ...
}

WriteReplaceWarningRequestIEs F1AP-PROTOCOL-IES ::= {
   { ID id-TransactionID CRITICALITY reject TYPE TransactionID PRESENCE mandatory }|
   { ID id-PWSSystemInformation CRITICALITY reject TYPE PWSSystemInformation PRESENCE mandatory }|
   { ID id-RepetitionPeriod CRITICALITY reject TYPE RepetitionPeriod PRESENCE mandatory }|
   { ID id-NumberofBroadcastRequest CRITICALITY reject TYPE NumberofBroadcastRequest PRESENCE mandatory }|
   { ID id-Cells-To-Be-Broadcast-List CRITICALITY reject TYPE Cells-To-Be-Broadcast-List PRESENCE optional },
   ...
}

Cells-To-Be-Broadcast-List ::= SEQUENCE (SIZE(1.. maxCellingNBDU)) OF ProtocolIE-SingleContainer { { Cells-To-Be-Broadcast-List-ItemIEs } }

Cells-To-Be-Broadcast-List-ItemIEs F1AP-PROTOCOL-IES ::= {
   { ID id-Cells-To-Be-Broadcast-Item CRITICALITY reject TYPE Cells-To-Be-Broadcast-Item PRESENCE mandatory },
   ...
}

-- **************************************************************
--
-- Write-Replace Warning Response
--
-- **************************************************************

WriteReplaceWarningResponse ::= SEQUENCE {
   protocolIEs ProtocolIE-Container { {WriteReplaceWarningResponseIEs} },
   ...
}

WriteReplaceWarningResponseIEs F1AP-PROTOCOL-IES ::= {
   { ID id-TransactionID CRITICALITY reject TYPE TransactionID PRESENCE mandatory }|
   { ID id-Cells-Broadcast-Completed-List CRITICALITY reject TYPE Cells-Broadcast-Completed-List PRESENCE optional }|
   { ID id-CriticalityDiagnostics CRITICALITY ignore TYPE CriticalityDiagnostics PRESENCE optional }|
   { ID id-Dedicated-SIDelivery-NeededUE-List CRITICALITY ignore TYPE Dedicated-SIDelivery-NeededUE-List PRESENCE optional },
   ...
}

Cells-Broadcast-Completed-List ::= SEQUENCE (SIZE(1.. maxCellingNBDU)) OF ProtocolIE-SingleContainer { { Cells-Broadcast-Completed-List-ItemIEs } }

Cells-Broadcast-Completed-List-ItemIEs F1AP-PROTOCOL-IES ::= {
   { ID id-Cells-Broadcast-Completed-Item CRITICALITY reject TYPE Cells-Broadcast-Completed-Item PRESENCE mandatory },
   ...
}

-- **************************************************************
--
-- PWS CANCEL ELEMENTARY PROCEDURE
--
-- **************************************************************

-- **************************************************************
--
-- PWS Cancel Request
--
-- **************************************************************

PWSCancelRequest ::= SEQUENCE {
   protocolIEs ProtocolIE-Container { {PWSCancelRequestIEs} },
   ...
}

PWSCancelRequestIEs F1AP-PROTOCOL-IES ::= {
   { ID id-TransactionID CRITICALITY reject TYPE TransactionID PRESENCE mandatory }|
   { ID id-NumberofBroadcastRequest CRITICALITY reject TYPE NumberofBroadcastRequest PRESENCE mandatory }|
   { ID id-Broadcast-To-Be-Cancelled-List CRITICALITY reject TYPE Broadcast-To-Be-Cancelled-List PRESENCE optional }|
   { ID id-Cancel-all-Warning-Messages-Indicator CRITICALITY reject TYPE Cancel-all-Warning-Messages-Indicator PRESENCE optional }|
   { ID id-NotificationInformation CRITICALITY reject TYPE NotificationInformation PRESENCE optional},
   ...
}

Broadcast-To-Be-Cancelled-List ::= SEQUENCE (SIZE(1.. maxCellingNBDU)) OF ProtocolIE-SingleContainer { { Broadcast-To-Be-Cancelled-List-ItemIEs } }

Broadcast-To-Be-Cancelled-List-ItemIEs F1AP-PROTOCOL-IES ::= {
   { ID id-Broadcast-To-Be-Cancelled-Item CRITICALITY reject TYPE Broadcast-To-Be-Cancelled-Item PRESENCE mandatory },
   ...
}

-- **************************************************************
--
-- PWS Cancel Response
--
-- **************************************************************

PWSCancelResponse ::= SEQUENCE {
   protocolIEs ProtocolIE-Container { {PWSCancelResponseIEs} },
   ...
}

PWSCancelResponseIEs F1AP-PROTOCOL-IES ::= {
   { ID id-TransactionID CRITICALITY reject TYPE TransactionID PRESENCE mandatory }|
   { ID id-Cells-Broadcast-Cancelled-List CRITICALITY reject TYPE Cells-Broadcast-Cancelled-List PRESENCE optional }|
   { ID id-CriticalityDiagnostics CRITICALITY ignore TYPE CriticalityDiagnostics PRESENCE optional },
   ...
}

Cells-Broadcast-Cancelled-List ::= SEQUENCE (SIZE(1.. maxCellingNBDU)) OF ProtocolIE-SingleContainer { { Cells-Broadcast-Cancelled-List-ItemIEs } }

Cells-Broadcast-Cancelled-List-ItemIEs F1AP-PROTOCOL-IES ::= {
   { ID id-Cells-Broadcast-Cancelled-Item CRITICALITY reject TYPE Cells-Broadcast-Cancelled-Item PRESENCE mandatory },
   ...
}

-- **************************************************************
--
-- UE Inactivity Notification ELEMENTARY PROCEDURE
--
-- **************************************************************

-- **************************************************************
--
-- UE Inactivity Notification
--
-- **************************************************************

UEInactivityNotification ::= SEQUENCE {
   protocolIEs ProtocolIE-Container {{ UEInactivityNotificationIEs}},
   ...
}

UEInactivityNotificationIEs F1AP-PROTOCOL-IES ::= {
   { ID id-gNB-CU-UE-F1AP-ID CRITICALITY reject TYPE GNB-CU-UE-F1AP-ID PRESENCE mandatory }|
   { ID id-gNB-DU-UE-F1AP-ID CRITICALITY reject TYPE GNB-DU-UE-F1AP-ID PRESENCE mandatory }|
   { ID id-DRB-Activity-List CRITICALITY reject TYPE DRB-Activity-List PRESENCE mandatory } ,
   ...
}

DRB-Activity-List::= SEQUENCE (SIZE(1..maxnoofDRBs)) OF ProtocolIE-SingleContainer { { DRB-Activity-ItemIEs } }

DRB-Activity-ItemIEs F1AP-PROTOCOL-IES ::= {
   { ID id-DRB-Activity-Item CRITICALITY reject TYPE DRB-Activity-Item PRESENCE mandatory},
   ...
}

-- **************************************************************
--
-- Initial UL RRC Message Transfer ELEMENTARY PROCEDURE
--
-- **************************************************************

-- **************************************************************
--
-- INITIAL UL RRC Message Transfer
--
-- **************************************************************

InitialULRRCMessageTransfer ::= SEQUENCE {
   protocolIEs ProtocolIE-Container {{ InitialULRRCMessageTransferIEs}},
   ...
}

InitialULRRCMessageTransferIEs F1AP-PROTOCOL-IES ::= {
   { ID id-gNB-DU-UE-F1AP-ID CRITICALITY reject TYPE GNB-DU-UE-F1AP-ID PRESENCE mandatory }|
   { ID id-NRCGI CRITICALITY reject TYPE NRCGI PRESENCE mandatory }|
   { ID id-C-RNTI CRITICALITY reject TYPE C-RNTI PRESENCE mandatory }|
   { ID id-RRCContainer CRITICALITY reject TYPE RRCContainer PRESENCE mandatory }|
   { ID id-DUtoCURRCContainer CRITICALITY reject TYPE DUtoCURRCContainer PRESENCE optional }|
   { ID id-SULAccessIndication CRITICALITY ignore TYPE SULAccessIndication PRESENCE optional }|
   { ID id-TransactionID CRITICALITY ignore TYPE TransactionID PRESENCE mandatory }|
   { ID id-RANUEID CRITICALITY ignore TYPE RANUEID PRESENCE optional }|
   { ID id-RRCContainer-RRCSetupComplete CRITICALITY ignore TYPE RRCContainer-RRCSetupComplete PRESENCE optional },
   ...
}

-- **************************************************************
--
-- DL RRC Message Transfer ELEMENTARY PROCEDURE
--
-- **************************************************************

-- **************************************************************
--
-- DL RRC Message Transfer
--
-- **************************************************************

DLRRCMessageTransfer ::= SEQUENCE {
   protocolIEs ProtocolIE-Container {{ DLRRCMessageTransferIEs}},
   ...
}

DLRRCMessageTransferIEs F1AP-PROTOCOL-IES ::= {
   { ID id-gNB-CU-UE-F1AP-ID CRITICALITY reject TYPE GNB-CU-UE-F1AP-ID PRESENCE mandatory }|
   { ID id-gNB-DU-UE-F1AP-ID CRITICALITY reject TYPE GNB-DU-UE-F1AP-ID PRESENCE mandatory }|
   { ID id-oldgNB-DU-UE-F1AP-ID CRITICALITY reject TYPE GNB-DU-UE-F1AP-ID PRESENCE optional }|
   { ID id-SRBID CRITICALITY reject TYPE SRBID PRESENCE mandatory }|
   { ID id-ExecuteDuplication CRITICALITY ignore TYPE ExecuteDuplication PRESENCE optional}|
   { ID id-RRCContainer CRITICALITY reject TYPE RRCContainer PRESENCE mandatory }|
   { ID id-RAT-FrequencyPriorityInformation CRITICALITY reject TYPE RAT-FrequencyPriorityInformation PRESENCE optional }|
   { ID id-RRCDeliveryStatusRequest CRITICALITY ignore TYPE RRCDeliveryStatusRequest PRESENCE optional }|
   { ID id-UEContextNotRetrievable CRITICALITY reject TYPE UEContextNotRetrievable PRESENCE optional }|
   { ID id-RedirectedRRCmessage CRITICALITY reject TYPE OCTET STRING PRESENCE optional }|
   { ID id-PLMNAssistanceInfoForNetShar CRITICALITY ignore TYPE PLMN-Identity PRESENCE optional }|
   { ID id-new-gNB-CU-UE-F1AP-ID CRITICALITY reject TYPE GNB-CU-UE-F1AP-ID PRESENCE optional }|
   { ID id-AdditionalRRMPriorityIndex CRITICALITY ignore TYPE AdditionalRRMPriorityIndex PRESENCE optional },
   ...
}
-- **************************************************************
--
-- UL RRC Message Transfer ELEMENTARY PROCEDURE
--
-- **************************************************************

-- **************************************************************
--
-- UL RRC Message Transfer
--
-- **************************************************************

ULRRCMessageTransfer ::= SEQUENCE {
   protocolIEs ProtocolIE-Container {{ ULRRCMessageTransferIEs}},
   ...
}

ULRRCMessageTransferIEs F1AP-PROTOCOL-IES ::= {
   { ID id-gNB-CU-UE-F1AP-ID CRITICALITY reject TYPE GNB-CU-UE-F1AP-ID PRESENCE mandatory }|
   { ID id-gNB-DU-UE-F1AP-ID CRITICALITY reject TYPE GNB-DU-UE-F1AP-ID PRESENCE mandatory }|
   { ID id-SRBID CRITICALITY reject TYPE SRBID PRESENCE mandatory }|
   { ID id-RRCContainer CRITICALITY reject TYPE RRCContainer PRESENCE mandatory }|
   { ID id-SelectedPLMNID CRITICALITY reject TYPE PLMN-Identity PRESENCE optional }|
   { ID id-new-gNB-DU-UE-F1AP-ID CRITICALITY reject TYPE GNB-DU-UE-F1AP-ID PRESENCE optional },
   ...
}

-- **************************************************************
--
-- PRIVATE MESSAGE
--
-- **************************************************************

PrivateMessage ::= SEQUENCE {
   privateIEs PrivateIE-Container {{PrivateMessage-IEs}},
   ...
}

PrivateMessage-IEs F1AP-PRIVATE-IES ::= {
   ...
}

-- **************************************************************
--
-- System Information ELEMENTARY PROCEDURE
--
-- **************************************************************

-- **************************************************************
--
-- System information Delivery Command
--
-- **************************************************************

SystemInformationDeliveryCommand ::= SEQUENCE {
   protocolIEs ProtocolIE-Container {{ SystemInformationDeliveryCommandIEs}},
   ...
}

SystemInformationDeliveryCommandIEs F1AP-PROTOCOL-IES ::= {
   { ID id-TransactionID CRITICALITY reject TYPE TransactionID PRESENCE mandatory }|
   { ID id-NRCGI CRITICALITY reject TYPE NRCGI PRESENCE mandatory }|
   { ID id-SItype-List CRITICALITY reject TYPE SItype-List PRESENCE mandatory }|
   { ID id-ConfirmedUEID CRITICALITY reject TYPE GNB-DU-UE-F1AP-ID PRESENCE mandatory },
   ...
}

-- **************************************************************
--
-- Paging PROCEDURE
--
-- **************************************************************

-- **************************************************************
--
-- Paging
--
-- **************************************************************

Paging ::= SEQUENCE {
   protocolIEs ProtocolIE-Container {{ PagingIEs}},
   ...
}

PagingIEs F1AP-PROTOCOL-IES ::= {
   { ID id-UEIdentityIndexValue CRITICALITY reject TYPE UEIdentityIndexValue PRESENCE mandatory }|
   { ID id-PagingIdentity CRITICALITY reject TYPE PagingIdentity PRESENCE mandatory }|
   { ID id-PagingDRX CRITICALITY ignore TYPE PagingDRX PRESENCE optional }|
   { ID id-PagingPriority CRITICALITY ignore TYPE PagingPriority PRESENCE optional }|
   { ID id-PagingCell-List CRITICALITY ignore TYPE PagingCell-list PRESENCE mandatory }|
   { ID id-PagingOrigin CRITICALITY ignore TYPE PagingOrigin PRESENCE optional },
   ...
}

PagingCell-list::= SEQUENCE (SIZE(1.. maxnoofPagingCells)) OF ProtocolIE-SingleContainer { { PagingCell-ItemIEs } }

PagingCell-ItemIEs F1AP-PROTOCOL-IES ::= {
   { ID id-PagingCell-Item CRITICALITY ignore TYPE PagingCell-Item PRESENCE mandatory} ,
   ...
}

-- **************************************************************
--
-- Notify
--
-- **************************************************************

Notify ::= SEQUENCE {
   protocolIEs ProtocolIE-Container {{ NotifyIEs}},
   ...
}

NotifyIEs F1AP-PROTOCOL-IES ::= {
   { ID id-gNB-CU-UE-F1AP-ID CRITICALITY reject TYPE GNB-CU-UE-F1AP-ID PRESENCE mandatory }|
   { ID id-gNB-DU-UE-F1AP-ID CRITICALITY reject TYPE GNB-DU-UE-F1AP-ID PRESENCE mandatory }|
   { ID id-DRB-Notify-List CRITICALITY reject TYPE DRB-Notify-List PRESENCE mandatory },
   ...
}

DRB-Notify-List::= SEQUENCE (SIZE(1.. maxnoofDRBs)) OF ProtocolIE-SingleContainer { { DRB-Notify-ItemIEs } }

DRB-Notify-ItemIEs F1AP-PROTOCOL-IES ::= {
   { ID id-DRB-Notify-Item CRITICALITY reject TYPE DRB-Notify-Item PRESENCE mandatory},
   ...
}

-- **************************************************************
--
-- NETWORK ACCESS RATE REDUCTION ELEMENTARY PROCEDURE
--
-- **************************************************************

-- **************************************************************
--
-- Network Access Rate Reduction
--
-- **************************************************************

NetworkAccessRateReduction ::= SEQUENCE {
   protocolIEs ProtocolIE-Container {{ NetworkAccessRateReductionIEs }},
   ...
}

NetworkAccessRateReductionIEs F1AP-PROTOCOL-IES ::= {
   { ID id-TransactionID CRITICALITY reject TYPE TransactionID PRESENCE mandatory }|
   { ID id-UAC-Assistance-Info CRITICALITY reject TYPE UAC-Assistance-Info PRESENCE mandatory },
   ...
}

-- **************************************************************
--
-- PWS RESTART INDICATION ELEMENTARY PROCEDURE
--
-- **************************************************************

-- **************************************************************
--
-- PWS Restart Indication
--
-- **************************************************************

PWSRestartIndication ::= SEQUENCE {
   protocolIEs ProtocolIE-Container { { PWSRestartIndicationIEs} },
   ...
}

PWSRestartIndicationIEs F1AP-PROTOCOL-IES ::= {
   { ID id-TransactionID CRITICALITY reject TYPE TransactionID PRESENCE mandatory }|
   { ID id-NR-CGI-List-For-Restart-List CRITICALITY reject TYPE NR-CGI-List-For-Restart-List PRESENCE mandatory },
   ...
}

NR-CGI-List-For-Restart-List ::= SEQUENCE (SIZE(1.. maxCellingNBDU)) OF ProtocolIE-SingleContainer { { NR-CGI-List-For-Restart-List-ItemIEs } }

NR-CGI-List-For-Restart-List-ItemIEs F1AP-PROTOCOL-IES ::= {
   { ID id-NR-CGI-List-For-Restart-Item CRITICALITY reject TYPE NR-CGI-List-For-Restart-Item PRESENCE mandatory },
   ...
}

-- **************************************************************
--
-- PWS FAILURE INDICATION ELEMENTARY PROCEDURE
--
-- **************************************************************

-- **************************************************************
--
-- PWS Failure Indication
--
-- **************************************************************

PWSFailureIndication ::= SEQUENCE {
   protocolIEs ProtocolIE-Container { { PWSFailureIndicationIEs} },
   ...
}

PWSFailureIndicationIEs F1AP-PROTOCOL-IES ::= {
   { ID id-TransactionID CRITICALITY reject TYPE TransactionID PRESENCE mandatory }|
   { ID id-PWS-Failed-NR-CGI-List CRITICALITY reject TYPE PWS-Failed-NR-CGI-List PRESENCE optional },
   ...
}

PWS-Failed-NR-CGI-List ::= SEQUENCE (SIZE(1.. maxCellingNBDU)) OF ProtocolIE-SingleContainer { { PWS-Failed-NR-CGI-List-ItemIEs } }

PWS-Failed-NR-CGI-List-ItemIEs F1AP-PROTOCOL-IES ::= {
   { ID id-PWS-Failed-NR-CGI-Item CRITICALITY reject TYPE PWS-Failed-NR-CGI-Item PRESENCE mandatory },
   ...
}

-- **************************************************************
--
-- gNB-DU STATUS INDICATION ELEMENTARY PROCEDURE
--
-- **************************************************************

-- **************************************************************
--
-- gNB-DU Status Indication
--
-- **************************************************************

GNBDUStatusIndication ::= SEQUENCE {
   protocolIEs ProtocolIE-Container { {GNBDUStatusIndicationIEs} },
   ...
}

GNBDUStatusIndicationIEs F1AP-PROTOCOL-IES ::= {
   { ID id-TransactionID CRITICALITY reject TYPE TransactionID PRESENCE mandatory }|
   { ID id-GNBDUOverloadInformation CRITICALITY reject TYPE GNBDUOverloadInformation PRESENCE mandatory },
   ...
}

-- **************************************************************
--
-- RRC Delivery Report ELEMENTARY PROCEDURE
--
-- **************************************************************

-- **************************************************************
--
-- RRC Delivery Report
--
-- **************************************************************

RRCDeliveryReport ::= SEQUENCE {
   protocolIEs ProtocolIE-Container {{ RRCDeliveryReportIEs}},
   ...
}

RRCDeliveryReportIEs F1AP-PROTOCOL-IES ::= {
   { ID id-gNB-CU-UE-F1AP-ID CRITICALITY reject TYPE GNB-CU-UE-F1AP-ID PRESENCE mandatory }|
   { ID id-gNB-DU-UE-F1AP-ID CRITICALITY reject TYPE GNB-DU-UE-F1AP-ID PRESENCE mandatory }|
   { ID id-RRCDeliveryStatus CRITICALITY ignore TYPE RRCDeliveryStatus PRESENCE mandatory }|
   { ID id-SRBID CRITICALITY ignore TYPE SRBID PRESENCE mandatory },
   ...
}

-- **************************************************************
--
-- F1 Removal ELEMENTARY PROCEDURE
--
-- **************************************************************

-- **************************************************************
--
-- F1 Removal Request
--
-- **************************************************************

F1RemovalRequest ::= SEQUENCE {
   protocolIEs ProtocolIE-Container {{ F1RemovalRequestIEs }},
   ...
}

F1RemovalRequestIEs F1AP-PROTOCOL-IES ::= {
   { ID id-TransactionID CRITICALITY reject TYPE TransactionID PRESENCE mandatory },
   ...
}

-- **************************************************************
--
-- F1 Removal Response
--
-- **************************************************************

F1RemovalResponse ::= SEQUENCE {
   protocolIEs ProtocolIE-Container {{ F1RemovalResponseIEs }},
   ...
}

F1RemovalResponseIEs F1AP-PROTOCOL-IES ::= {
   { ID id-TransactionID CRITICALITY reject TYPE TransactionID PRESENCE mandatory }|
   { ID id-CriticalityDiagnostics CRITICALITY ignore TYPE CriticalityDiagnostics PRESENCE optional },

   ...
}

-- **************************************************************
--
-- F1 Removal Failure
--
-- **************************************************************

F1RemovalFailure ::= SEQUENCE {
   protocolIEs ProtocolIE-Container {{ F1RemovalFailureIEs }},
   ...
}

F1RemovalFailureIEs F1AP-PROTOCOL-IES ::= {
   { ID id-TransactionID CRITICALITY reject TYPE TransactionID PRESENCE mandatory }|
   { ID id-Cause CRITICALITY ignore TYPE Cause PRESENCE mandatory }|
   { ID id-CriticalityDiagnostics CRITICALITY ignore TYPE CriticalityDiagnostics PRESENCE optional },

   ...
}

-- **************************************************************
--
-- TRACE ELEMENTARY PROCEDURES
--
-- **************************************************************

-- **************************************************************
--
-- TRACE START
--
-- **************************************************************

TraceStart ::= SEQUENCE {
   protocolIEs ProtocolIE-Container { {TraceStartIEs} },
   ...
}

TraceStartIEs F1AP-PROTOCOL-IES ::= {
   { ID id-gNB-CU-UE-F1AP-ID CRITICALITY reject TYPE GNB-CU-UE-F1AP-ID PRESENCE mandatory }|
   { ID id-gNB-DU-UE-F1AP-ID CRITICALITY reject TYPE GNB-DU-UE-F1AP-ID PRESENCE mandatory }|
   { ID id-TraceActivation CRITICALITY ignore TYPE TraceActivation PRESENCE mandatory },
   ...
}

-- **************************************************************
--
-- DEACTIVATE TRACE
--
-- **************************************************************

DeactivateTrace ::= SEQUENCE {
   protocolIEs ProtocolIE-Container { {DeactivateTraceIEs} },
   ...
}

DeactivateTraceIEs F1AP-PROTOCOL-IES ::= {
   { ID id-gNB-CU-UE-F1AP-ID CRITICALITY reject TYPE GNB-CU-UE-F1AP-ID PRESENCE mandatory }|
   { ID id-gNB-DU-UE-F1AP-ID CRITICALITY reject TYPE GNB-DU-UE-F1AP-ID PRESENCE mandatory }|
   { ID id-TraceID CRITICALITY ignore TYPE TraceID PRESENCE mandatory },
   ...
}

-- **************************************************************
--
-- CELL TRAFFIC TRACE
--
-- **************************************************************

CellTrafficTrace ::= SEQUENCE {
   protocolIEs ProtocolIE-Container { {CellTrafficTraceIEs} },
   ...
}

CellTrafficTraceIEs F1AP-PROTOCOL-IES ::= {
   { ID id-gNB-CU-UE-F1AP-ID CRITICALITY reject TYPE GNB-CU-UE-F1AP-ID PRESENCE mandatory }|
   { ID id-gNB-DU-UE-F1AP-ID CRITICALITY reject TYPE GNB-DU-UE-F1AP-ID PRESENCE mandatory }|
   {ID id-TraceID CRITICALITY ignore TYPE TraceID PRESENCE mandatory }|
   {ID id-TraceCollectionEntityIPAddress CRITICALITY ignore TYPE TransportLayerAddress PRESENCE mandatory }|
   {ID id-PrivacyIndicator CRITICALITY ignore TYPE PrivacyIndicator PRESENCE optional }|

   {ID id-TraceCollectionEntityURI CRITICALITY ignore TYPE URI-address PRESENCE optional },
   ...

}

-- **************************************************************
--
-- DU-CU Radio Information Transfer ELEMENTARY PROCEDURE
--
-- **************************************************************

-- **************************************************************
--
-- DU-CU Radio Information Transfer
--
-- **************************************************************

DUCURadioInformationTransfer ::= SEQUENCE {
   protocolIEs ProtocolIE-Container {{ DUCURadioInformationTransferIEs}},
   ...
}

DUCURadioInformationTransferIEs F1AP-PROTOCOL-IES ::= {
   { ID id-TransactionID CRITICALITY reject TYPE TransactionID PRESENCE mandatory }|
   { ID id-DUCURadioInformationType CRITICALITY ignore TYPE DUCURadioInformationType PRESENCE mandatory },
   ...
}

-- **************************************************************
--
-- CU-DU Radio Information Transfer ELEMENTARY PROCEDURE
--
-- **************************************************************

-- **************************************************************
--
-- CU-DU Radio Information Transfer
--
-- **************************************************************

CUDURadioInformationTransfer ::= SEQUENCE {
   protocolIEs ProtocolIE-Container {{ CUDURadioInformationTransferIEs}},
   ...
}

CUDURadioInformationTransferIEs F1AP-PROTOCOL-IES ::= {
   { ID id-TransactionID CRITICALITY reject TYPE TransactionID PRESENCE mandatory }|
   { ID id-CUDURadioInformationType CRITICALITY ignore TYPE CUDURadioInformationType PRESENCE mandatory },
   ...
}

-- **************************************************************
--
-- IAB PROCEDURES
--
-- **************************************************************
-- **************************************************************
--
-- BAP Mapping Configuration ELEMENTARY PROCEDURE
--
-- **************************************************************

-- **************************************************************
--
-- BAP MAPPING CONFIGURATION
-- **************************************************************

BAPMappingConfiguration ::= SEQUENCE {
   protocolIEs ProtocolIE-Container { {BAPMappingConfiguration-IEs} },
   ...
}

BAPMappingConfiguration-IEs F1AP-PROTOCOL-IES ::= {
   { ID id-TransactionID CRITICALITY reject TYPE TransactionID PRESENCE mandatory}|
   { ID id-BH-Routing-Information-Added-List CRITICALITY ignore TYPE BH-Routing-Information-Added-List PRESENCE optional}|
   { ID id-BH-Routing-Information-Removed-List CRITICALITY ignore TYPE BH-Routing-Information-Removed-List PRESENCE optional}|
   { ID id-TrafficMappingInformation CRITICALITY ignore TYPE TrafficMappingInfo PRESENCE optional},
   ...
}

BH-Routing-Information-Added-List ::= SEQUENCE (SIZE(1.. maxnoofRoutingEntries)) OF ProtocolIE-SingleContainer { { BH-Routing-Information-Added-List-ItemIEs } }
BH-Routing-Information-Removed-List ::= SEQUENCE (SIZE(1.. maxnoofRoutingEntries)) OF ProtocolIE-SingleContainer { { BH-Routing-Information-Removed-List-ItemIEs } }

BH-Routing-Information-Added-List-ItemIEs F1AP-PROTOCOL-IES ::= {
   { ID id-BH-Routing-Information-Added-List-Item CRITICALITY ignore TYPE BH-Routing-Information-Added-List-Item PRESENCE optional},
   ...
}

BH-Routing-Information-Removed-List-ItemIEs F1AP-PROTOCOL-IES ::= {
   { ID id-BH-Routing-Information-Removed-List-Item CRITICALITY ignore TYPE BH-Routing-Information-Removed-List-Item PRESENCE optional},
   ...
}

-- **************************************************************
--
-- BAP MAPPING CONFIGURATION ACKNOWLEDGE
-- **************************************************************

BAPMappingConfigurationAcknowledge ::= SEQUENCE {
   protocolIEs ProtocolIE-Container { {BAPMappingConfigurationAcknowledge-IEs} },
   ...
}

BAPMappingConfigurationAcknowledge-IEs F1AP-PROTOCOL-IES ::= {
   { ID id-TransactionID CRITICALITY reject TYPE TransactionID PRESENCE mandatory}|
   { ID id-CriticalityDiagnostics CRITICALITY ignore TYPE CriticalityDiagnostics PRESENCE optional},
   ...
}

-- **************************************************************
--
-- BAP MAPPING CONFIGURATION FAILURE
--
-- **************************************************************

BAPMappingConfigurationFailure ::= SEQUENCE {
   protocolIEs ProtocolIE-Container { { BAPMappingConfigurationFailureIEs} },
   ...
}

BAPMappingConfigurationFailureIEs F1AP-PROTOCOL-IES ::= {
   { ID id-TransactionID CRITICALITY reject TYPE TransactionID PRESENCE mandatory }|
   { ID id-Cause CRITICALITY ignore TYPE Cause PRESENCE mandatory }|
   { ID id-TimeToWait CRITICALITY ignore TYPE TimeToWait PRESENCE optional }|
   { ID id-CriticalityDiagnostics CRITICALITY ignore TYPE CriticalityDiagnostics PRESENCE optional },
   ...
}

-- **************************************************************
--
-- GNB-DU Configuration ELEMENTARY PROCEDURE
--
-- **************************************************************

-- **************************************************************
--
-- GNB-DU RESOURCE CONFIGURATION
-- **************************************************************

GNBDUResourceConfiguration ::= SEQUENCE {
   protocolIEs ProtocolIE-Container {{ GNBDUResourceConfigurationIEs}},
   ...
}

GNBDUResourceConfigurationIEs F1AP-PROTOCOL-IES ::= {
   { ID id-TransactionID CRITICALITY reject TYPE TransactionID PRESENCE mandatory }|
   { ID id-Activated-Cells-to-be-Updated-List CRITICALITY reject TYPE Activated-Cells-to-be-Updated-List PRESENCE optional}|
   { ID id-Child-Nodes-List CRITICALITY reject TYPE Child-Nodes-List PRESENCE optional},
   ...
}

-- **************************************************************
--
-- GNB-DU RESOURCE CONFIGURATION ACKNOWLEDGE
-- **************************************************************

GNBDUResourceConfigurationAcknowledge ::= SEQUENCE {
   protocolIEs ProtocolIE-Container { { GNBDUResourceConfigurationAcknowledgeIEs} },
   ...
}

GNBDUResourceConfigurationAcknowledgeIEs F1AP-PROTOCOL-IES ::= {
   { ID id-TransactionID CRITICALITY reject TYPE TransactionID PRESENCE mandatory }|
   { ID id-CriticalityDiagnostics CRITICALITY ignore TYPE CriticalityDiagnostics PRESENCE optional },
   ...
}

-- **************************************************************
--
-- GNB-DU RESOURCE CONFIGURATION FAILURE
--
-- **************************************************************

GNBDUResourceConfigurationFailure ::= SEQUENCE {
   protocolIEs ProtocolIE-Container { { GNBDUResourceConfigurationFailureIEs} },
   ...
}

GNBDUResourceConfigurationFailureIEs F1AP-PROTOCOL-IES ::= {
   { ID id-TransactionID CRITICALITY reject TYPE TransactionID PRESENCE mandatory }|
   { ID id-Cause CRITICALITY ignore TYPE Cause PRESENCE mandatory }|
   { ID id-TimeToWait CRITICALITY ignore TYPE TimeToWait PRESENCE optional }|
   { ID id-CriticalityDiagnostics CRITICALITY ignore TYPE CriticalityDiagnostics PRESENCE optional },
   ...
}

-- **************************************************************
--
-- IAB TNL Address Allocation ELEMENTARY PROCEDURE
--
-- **************************************************************

-- **************************************************************
--
-- IAB TNL ADDRESS REQUEST
-- **************************************************************

IABTNLAddressRequest ::= SEQUENCE {
   protocolIEs ProtocolIE-Container { {IABTNLAddressRequestIEs} },
   ...
}

IABTNLAddressRequestIEs F1AP-PROTOCOL-IES ::= {
   { ID id-TransactionID CRITICALITY reject TYPE TransactionID PRESENCE mandatory }|
   { ID id-IABv4AddressesRequested CRITICALITY reject TYPE IABv4AddressesRequested PRESENCE optional }|
   { ID id-IABIPv6RequestType CRITICALITY reject TYPE IABIPv6RequestType PRESENCE optional }|
   { ID id-IAB-TNL-Addresses-To-Remove-List CRITICALITY reject TYPE IAB-TNL-Addresses-To-Remove-List PRESENCE optional },
   ...
}

IAB-TNL-Addresses-To-Remove-List ::= SEQUENCE (SIZE(1..maxnoofTLAsIAB)) OF ProtocolIE-SingleContainer { { IAB-TNL-Addresses-To-Remove-ItemIEs } }

IAB-TNL-Addresses-To-Remove-ItemIEs F1AP-PROTOCOL-IES::= {
   { ID id-IAB-TNL-Addresses-To-Remove-Item CRITICALITY reject TYPE IAB-TNL-Addresses-To-Remove-Item PRESENCE mandatory},
   ...
}

-- **************************************************************
--
-- IAB TNL ADDRESS RESPONSE
-- **************************************************************

IABTNLAddressResponse ::= SEQUENCE {
   protocolIEs ProtocolIE-Container { {IABTNLAddressResponseIEs} },
   ...
}

IABTNLAddressResponseIEs F1AP-PROTOCOL-IES ::= {
   { ID id-TransactionID CRITICALITY reject TYPE TransactionID PRESENCE mandatory }|
   { ID id-IAB-Allocated-TNL-Address-List CRITICALITY reject TYPE IAB-Allocated-TNL-Address-List PRESENCE mandatory },
   ...
}

IAB-Allocated-TNL-Address-List ::= SEQUENCE (SIZE(1.. maxnoofTLAsIAB)) OF ProtocolIE-SingleContainer { { IAB-Allocated-TNL-Address-List-ItemIEs } }

IAB-Allocated-TNL-Address-List-ItemIEs F1AP-PROTOCOL-IES::= {
   { ID id-IAB-Allocated-TNL-Address-Item CRITICALITY reject TYPE IAB-Allocated-TNL-Address-Item PRESENCE mandatory},
   ...
}

-- **************************************************************
--
-- IAB TNL ADDRESS FAILURE
--
-- **************************************************************

IABTNLAddressFailure ::= SEQUENCE {
   protocolIEs ProtocolIE-Container { { IABTNLAddressFailureIEs} },
   ...
}

IABTNLAddressFailureIEs F1AP-PROTOCOL-IES ::= {
   { ID id-TransactionID CRITICALITY reject TYPE TransactionID PRESENCE mandatory }|
   { ID id-Cause CRITICALITY ignore TYPE Cause PRESENCE mandatory }|
   { ID id-TimeToWait CRITICALITY ignore TYPE TimeToWait PRESENCE optional }|
   { ID id-CriticalityDiagnostics CRITICALITY ignore TYPE CriticalityDiagnostics PRESENCE optional },
   ...
}

-- **************************************************************
--
-- IAB UP Configuration Update ELEMENTARY PROCEDURE
--
-- **************************************************************

-- **************************************************************
--
-- IAB UP Configuration Update Request
--
-- **************************************************************

IABUPConfigurationUpdateRequest ::= SEQUENCE {
   protocolIEs ProtocolIE-Container { { IABUPConfigurationUpdateRequestIEs} },
   ...
}

IABUPConfigurationUpdateRequestIEs F1AP-PROTOCOL-IES ::= {
   { ID id-TransactionID CRITICALITY reject TYPE TransactionID PRESENCE mandatory }|
   { ID id-UL-UP-TNL-Information-to-Update-List CRITICALITY ignore TYPE UL-UP-TNL-Information-to-Update-List PRESENCE optional }|
   { ID id-UL-UP-TNL-Address-to-Update-List CRITICALITY ignore TYPE UL-UP-TNL-Address-to-Update-List PRESENCE optional },
   ...
}

UL-UP-TNL-Information-to-Update-List ::= SEQUENCE (SIZE(1.. maxnoofULUPTNLInformationforIAB)) OF ProtocolIE-SingleContainer { { UL-UP-TNL-Information-to-Update-List-ItemIEs } }

UL-UP-TNL-Information-to-Update-List-ItemIEs F1AP-PROTOCOL-IES ::= {
   { ID id-UL-UP-TNL-Information-to-Update-List-Item CRITICALITY ignore TYPE UL-UP-TNL-Information-to-Update-List-Item PRESENCE optional},
   ...
}

UL-UP-TNL-Address-to-Update-List ::= SEQUENCE (SIZE(1.. maxnoofUPTNLAddresses)) OF ProtocolIE-SingleContainer { { UL-UP-TNL-Address-to-Update-List-ItemIEs } }

UL-UP-TNL-Address-to-Update-List-ItemIEs F1AP-PROTOCOL-IES ::= {
   { ID id-UL-UP-TNL-Address-to-Update-List-Item CRITICALITY ignore TYPE UL-UP-TNL-Address-to-Update-List-Item PRESENCE optional},
   ...
}

-- **************************************************************
--
-- IAB UP Configuration Update Response
--
-- **************************************************************

IABUPConfigurationUpdateResponse ::= SEQUENCE {
   protocolIEs ProtocolIE-Container { { IABUPConfigurationUpdateResponseIEs} },
   ...
}

IABUPConfigurationUpdateResponseIEs F1AP-PROTOCOL-IES ::= {
   { ID id-TransactionID CRITICALITY reject TYPE TransactionID PRESENCE mandatory }|
   { ID id-CriticalityDiagnostics CRITICALITY ignore TYPE CriticalityDiagnostics PRESENCE optional }|
   { ID id-DL-UP-TNL-Address-to-Update-List CRITICALITY reject TYPE DL-UP-TNL-Address-to-Update-List PRESENCE optional },
   ...
}

DL-UP-TNL-Address-to-Update-List ::= SEQUENCE (SIZE(1.. maxnoofUPTNLAddresses)) OF ProtocolIE-SingleContainer { { DL-UP-TNL-Address-to-Update-List-ItemIEs } }

DL-UP-TNL-Address-to-Update-List-ItemIEs F1AP-PROTOCOL-IES ::= {
   { ID id-DL-UP-TNL-Address-to-Update-List-Item CRITICALITY ignore TYPE DL-UP-TNL-Address-to-Update-List-Item PRESENCE optional},
   ...
}

-- **************************************************************
--
-- IAB UP Configuration Update Failure
--
-- **************************************************************

IABUPConfigurationUpdateFailure ::= SEQUENCE {
   protocolIEs ProtocolIE-Container { { IABUPConfigurationUpdateFailureIEs} },
   ...
}

IABUPConfigurationUpdateFailureIEs F1AP-PROTOCOL-IES ::= {
   { ID id-TransactionID CRITICALITY reject TYPE TransactionID PRESENCE mandatory }|
   { ID id-Cause CRITICALITY ignore TYPE Cause PRESENCE mandatory }|
   { ID id-TimeToWait CRITICALITY ignore TYPE TimeToWait PRESENCE optional }|
   { ID id-CriticalityDiagnostics CRITICALITY ignore TYPE CriticalityDiagnostics PRESENCE optional },
   ...
}

-- **************************************************************
--
-- Resource Status Reporting Initiation ELEMENTARY PROCEDURE
--
-- **************************************************************

-- **************************************************************
--
-- Resource Status Request
--
-- **************************************************************

ResourceStatusRequest::= SEQUENCE {
   protocolIEs ProtocolIE-Container { {ResourceStatusRequestIEs} },
   ...
}

ResourceStatusRequestIEs F1AP-PROTOCOL-IES ::= {
   { ID id-TransactionID CRITICALITY reject TYPE TransactionID PRESENCE mandatory }|
   { ID id-gNBCUMeasurementID CRITICALITY reject TYPE GNBCUMeasurementID PRESENCE mandatory }|
   { ID id-gNBDUMeasurementID CRITICALITY ignore TYPE GNBDUMeasurementID PRESENCE conditional }|
   { ID id-RegistrationRequest CRITICALITY ignore TYPE RegistrationRequest PRESENCE mandatory }|
   { ID id-ReportCharacteristics CRITICALITY ignore TYPE ReportCharacteristics PRESENCE conditional }|
   { ID id-CellToReportList CRITICALITY ignore TYPE CellToReportList PRESENCE optional }|
   { ID id-ReportingPeriodicity CRITICALITY ignore TYPE ReportingPeriodicity PRESENCE optional },
   ...
}

-- **************************************************************
--
-- Resource Status Response
--
-- **************************************************************

ResourceStatusResponse ::= SEQUENCE {
   protocolIEs ProtocolIE-Container { { ResourceStatusResponseIEs} },
   ...
}

ResourceStatusResponseIEs F1AP-PROTOCOL-IES ::= {
   { ID id-TransactionID CRITICALITY reject TYPE TransactionID PRESENCE mandatory }|
   { ID id-gNBCUMeasurementID CRITICALITY reject TYPE GNBCUMeasurementID PRESENCE mandatory }|
   { ID id-gNBDUMeasurementID CRITICALITY ignore TYPE GNBDUMeasurementID PRESENCE mandatory }|
   { ID id-CriticalityDiagnostics CRITICALITY ignore TYPE CriticalityDiagnostics PRESENCE optional },
   ...
}

-- **************************************************************
--
-- Resource Status Failure
--
-- **************************************************************

ResourceStatusFailure ::= SEQUENCE {
   protocolIEs ProtocolIE-Container { { ResourceStatusFailureIEs} },
   ...
}

ResourceStatusFailureIEs F1AP-PROTOCOL-IES ::= {
   { ID id-TransactionID CRITICALITY reject TYPE TransactionID PRESENCE mandatory }|
   { ID id-gNBCUMeasurementID CRITICALITY reject TYPE GNBCUMeasurementID PRESENCE mandatory }|
   { ID id-gNBDUMeasurementID CRITICALITY ignore TYPE GNBDUMeasurementID PRESENCE mandatory }|
   { ID id-Cause CRITICALITY ignore TYPE Cause PRESENCE mandatory }|
   { ID id-CriticalityDiagnostics CRITICALITY ignore TYPE CriticalityDiagnostics PRESENCE optional },
   ...
}

-- **************************************************************
--
-- Resource Status Reporting ELEMENTARY PROCEDURE
--
-- **************************************************************

-- **************************************************************
--
-- Resource Status Update
--
-- **************************************************************

ResourceStatusUpdate ::= SEQUENCE {
   protocolIEs ProtocolIE-Container {{ ResourceStatusUpdateIEs}},
   ...
}

ResourceStatusUpdateIEs F1AP-PROTOCOL-IES ::= {
   { ID id-TransactionID CRITICALITY reject TYPE TransactionID PRESENCE mandatory }|
   { ID id-gNBCUMeasurementID CRITICALITY reject TYPE GNBCUMeasurementID PRESENCE mandatory }|
   { ID id-gNBDUMeasurementID CRITICALITY ignore TYPE GNBDUMeasurementID PRESENCE mandatory }|
   { ID id-HardwareLoadIndicator CRITICALITY ignore TYPE HardwareLoadIndicator PRESENCE optional }|
   { ID id-TNLCapacityIndicator CRITICALITY ignore TYPE TNLCapacityIndicator PRESENCE optional }|
   { ID id-CellMeasurementResultList CRITICALITY ignore TYPE CellMeasurementResultList PRESENCE optional },
   ...
}

-- **************************************************************
--
-- Access And Mobility Indication ELEMENTARY PROCEDURE
--
-- **************************************************************

-- **************************************************************
--
-- Access And Mobility Indication
--
-- **************************************************************

AccessAndMobilityIndication ::= SEQUENCE {
   protocolIEs ProtocolIE-Container { { AccessAndMobilityIndicationIEs} },
   ...
}

AccessAndMobilityIndicationIEs F1AP-PROTOCOL-IES ::= {
   { ID id-TransactionID CRITICALITY reject TYPE TransactionID PRESENCE mandatory }|
   { ID id-RACHReportInformationList CRITICALITY ignore TYPE RACHReportInformationList PRESENCE optional }|
   { ID id-RLFReportInformationList CRITICALITY ignore TYPE RLFReportInformationList PRESENCE optional },
   ...
}

-- **************************************************************
--
-- REFERENCE TIME INFORMATION REPORTING CONTROL
--
-- **************************************************************

ReferenceTimeInformationReportingControl::= SEQUENCE {
   protocolIEs ProtocolIE-Container { { ReferenceTimeInformationReportingControlIEs} },
   ...
}

ReferenceTimeInformationReportingControlIEs F1AP-PROTOCOL-IES ::= {
   { ID id-TransactionID CRITICALITY reject TYPE TransactionID PRESENCE mandatory }|
   { ID id-ReportingRequestType CRITICALITY reject TYPE ReportingRequestType PRESENCE mandatory },
   ...
}

-- **************************************************************
--
-- REFERENCE TIME INFORMATION REPORT
--
-- **************************************************************

ReferenceTimeInformationReport::= SEQUENCE {
   protocolIEs ProtocolIE-Container { { ReferenceTimeInformationReportIEs} },
   ...
}

ReferenceTimeInformationReportIEs F1AP-PROTOCOL-IES ::= {
   { ID id-TransactionID CRITICALITY ignore TYPE TransactionID PRESENCE mandatory }|
   { ID id-TimeReferenceInformation CRITICALITY ignore TYPE TimeReferenceInformation PRESENCE mandatory },
   ...
}

-- **************************************************************
--
-- Access Success
--
-- **************************************************************

AccessSuccess ::= SEQUENCE {
   protocolIEs ProtocolIE-Container {{ AccessSuccessIEs}},
   ...
}

AccessSuccessIEs F1AP-PROTOCOL-IES ::= {
   { ID id-gNB-CU-UE-F1AP-ID CRITICALITY reject TYPE GNB-CU-UE-F1AP-ID PRESENCE mandatory }|
   { ID id-gNB-DU-UE-F1AP-ID CRITICALITY reject TYPE GNB-DU-UE-F1AP-ID PRESENCE mandatory }|
   { ID id-NRCGI CRITICALITY reject TYPE NRCGI PRESENCE mandatory },
   ...
}

-- **************************************************************
--
-- POSITIONING ASSISTANCE INFORMATION CONTROL ELEMENTARY PROCEDURE
--
-- **************************************************************

-- **************************************************************
--
-- Positioning Assistance Information Control
--
-- **************************************************************

PositioningAssistanceInformationControl ::= SEQUENCE {
   protocolIEs ProtocolIE-Container {{ PositioningAssistanceInformationControlIEs}},
   ...
}

PositioningAssistanceInformationControlIEs F1AP-PROTOCOL-IES ::= {
   { ID id-TransactionID CRITICALITY reject TYPE TransactionID PRESENCE mandatory }|
   { ID id-PosAssistance-Information CRITICALITY reject TYPE PosAssistance-Information PRESENCE optional}|
   { ID id-PosBroadcast CRITICALITY reject TYPE PosBroadcast PRESENCE optional}|
   { ID id-PositioningBroadcastCells CRITICALITY reject TYPE PositioningBroadcastCells PRESENCE optional}|
   { ID id-RoutingID CRITICALITY reject TYPE RoutingID PRESENCE optional},
   ...
}

-- **************************************************************
--
-- POSITIONING ASSISTANCE INFORMATION FEEDBACK ELEMENTARY PROCEDURE
--
-- **************************************************************

-- **************************************************************
--
-- Positioning Assistance Information Feedback
--
-- **************************************************************

PositioningAssistanceInformationFeedback ::= SEQUENCE {
   protocolIEs ProtocolIE-Container {{ PositioningAssistanceInformationFeedbackIEs}},
   ...
}

PositioningAssistanceInformationFeedbackIEs F1AP-PROTOCOL-IES ::= {
   { ID id-TransactionID CRITICALITY reject TYPE TransactionID PRESENCE mandatory }|
   { ID id-PosAssistanceInformationFailureList CRITICALITY reject TYPE PosAssistanceInformationFailureList PRESENCE optional}|
   { ID id-PositioningBroadcastCells CRITICALITY reject TYPE PositioningBroadcastCells PRESENCE optional}|
   { ID id-RoutingID CRITICALITY reject TYPE RoutingID PRESENCE optional}|
   { ID id-CriticalityDiagnostics CRITICALITY ignore TYPE CriticalityDiagnostics PRESENCE optional},
   ...
}

-- **************************************************************
--
-- POSITONING MEASUREMENT EXCHANGE ELEMENTARY PROCEDURE
--
-- **************************************************************

-- **************************************************************
--
-- Positioning Measurement Request
--
-- **************************************************************

PositioningMeasurementRequest ::= SEQUENCE {
   protocolIEs ProtocolIE-Container { { PositioningMeasurementRequestIEs} },
   ...
}

PositioningMeasurementRequestIEs F1AP-PROTOCOL-IES ::= {
   { ID id-TransactionID CRITICALITY reject TYPE TransactionID PRESENCE mandatory}|
   { ID id-LMF-MeasurementID CRITICALITY reject TYPE LMF-MeasurementID PRESENCE mandatory}|
   { ID id-RAN-MeasurementID CRITICALITY reject TYPE RAN-MeasurementID PRESENCE mandatory}|
   { ID id-TRP-MeasurementRequestList CRITICALITY reject TYPE TRP-MeasurementRequestList PRESENCE mandatory}|
   { ID id-PosReportCharacteristics CRITICALITY reject TYPE PosReportCharacteristics PRESENCE mandatory}|
   { ID id-PosMeasurementPeriodicity CRITICALITY reject TYPE MeasurementPeriodicity PRESENCE conditional }|
   -- The above IE shall be present if the PosReportCharacteristics IE is set to “periodic” --
   { ID id-PosMeasurementQuantities CRITICALITY reject TYPE PosMeasurementQuantities PRESENCE mandatory}|
   { ID id-SFNInitialisationTime CRITICALITY ignore TYPE RelativeTime1900 PRESENCE optional }|
   { ID id-SRSConfiguration CRITICALITY ignore TYPE SRSConfiguration PRESENCE optional}|
   { ID id-MeasurementBeamInfoRequest CRITICALITY ignore TYPE MeasurementBeamInfoRequest PRESENCE optional }|
   { ID id-SystemFrameNumber CRITICALITY ignore TYPE SystemFrameNumber PRESENCE optional}|
   { ID id-SlotNumber CRITICALITY ignore TYPE SlotNumber PRESENCE optional},
   ...
}

-- **************************************************************
--
-- Positioning Measurement Response
--
-- **************************************************************

PositioningMeasurementResponse ::= SEQUENCE {
   protocolIEs ProtocolIE-Container { { PositioningMeasurementResponseIEs} },
   ...
}

PositioningMeasurementResponseIEs F1AP-PROTOCOL-IES ::= {
   { ID id-TransactionID CRITICALITY reject TYPE TransactionID PRESENCE mandatory}|
   { ID id-LMF-MeasurementID CRITICALITY reject TYPE LMF-MeasurementID PRESENCE mandatory}|
   { ID id-RAN-MeasurementID CRITICALITY reject TYPE RAN-MeasurementID PRESENCE mandatory}|
   { ID id-PosMeasurementResultList CRITICALITY reject TYPE PosMeasurementResultList PRESENCE optional }|
   { ID id-CriticalityDiagnostics CRITICALITY ignore TYPE CriticalityDiagnostics PRESENCE optional },
   ...
}

-- **************************************************************
--
-- Positioning Measurement Failure
--
-- **************************************************************

PositioningMeasurementFailure ::= SEQUENCE {
   protocolIEs ProtocolIE-Container { { PositioningMeasurementFailureIEs} },
   ...
}

PositioningMeasurementFailureIEs F1AP-PROTOCOL-IES ::= {
   { ID id-TransactionID CRITICALITY reject TYPE TransactionID PRESENCE mandatory }|
   { ID id-LMF-MeasurementID CRITICALITY reject TYPE LMF-MeasurementID PRESENCE mandatory }|
   { ID id-RAN-MeasurementID CRITICALITY reject TYPE RAN-MeasurementID PRESENCE mandatory }|
   { ID id-Cause CRITICALITY ignore TYPE Cause PRESENCE mandatory }|
   { ID id-CriticalityDiagnostics CRITICALITY ignore TYPE CriticalityDiagnostics PRESENCE optional },
   ...
}

-- **************************************************************
--
-- POSITIONING MEASUREMENT REPORT ELEMENTARY PROCEDURE
--
-- **************************************************************

-- **************************************************************
--
-- Positioning Measurement Report
--
-- **************************************************************

PositioningMeasurementReport ::= SEQUENCE {
   protocolIEs ProtocolIE-Container { { PositioningMeasurementReportIEs} },
   ...
}

PositioningMeasurementReportIEs F1AP-PROTOCOL-IES ::= {
   { ID id-TransactionID CRITICALITY reject TYPE TransactionID PRESENCE mandatory }|
   { ID id-LMF-MeasurementID CRITICALITY reject TYPE LMF-MeasurementID PRESENCE mandatory }|
   { ID id-RAN-MeasurementID CRITICALITY reject TYPE RAN-MeasurementID PRESENCE mandatory }|
   { ID id-PosMeasurementResultList CRITICALITY reject TYPE PosMeasurementResultList PRESENCE mandatory },
   ...
}

-- **************************************************************
--
-- POSITIONING MEASUREMENT ABORT ELEMENTARY PROCEDURE
--
-- **************************************************************

-- **************************************************************
--
-- Positioning Measurement Abort
--
-- **************************************************************

PositioningMeasurementAbort ::= SEQUENCE {
   protocolIEs ProtocolIE-Container { { PositioningMeasurementAbortIEs} },
   ...
}

PositioningMeasurementAbortIEs F1AP-PROTOCOL-IES ::= {
   { ID id-TransactionID CRITICALITY reject TYPE TransactionID PRESENCE mandatory }|
   { ID id-LMF-MeasurementID CRITICALITY reject TYPE LMF-MeasurementID PRESENCE mandatory }|
   { ID id-RAN-MeasurementID CRITICALITY reject TYPE RAN-MeasurementID PRESENCE mandatory },
   ...
}

-- **************************************************************
--
-- POSITIONING MEASUREMENT FAILURE INDICATION ELEMENTARY PROCEDURE
--
-- **************************************************************

-- **************************************************************
--
-- Positioning Measurement Failure Indication
--
-- **************************************************************

PositioningMeasurementFailureIndication ::= SEQUENCE {
   protocolIEs ProtocolIE-Container { { PositioningMeasurementFailureIndicationIEs} },
   ...
}

PositioningMeasurementFailureIndicationIEs F1AP-PROTOCOL-IES ::= {
   { ID id-TransactionID CRITICALITY reject TYPE TransactionID PRESENCE mandatory }|
   { ID id-LMF-MeasurementID CRITICALITY reject TYPE LMF-MeasurementID PRESENCE mandatory }|
   { ID id-RAN-MeasurementID CRITICALITY reject TYPE RAN-MeasurementID PRESENCE mandatory }|
   { ID id-Cause CRITICALITY ignore TYPE Cause PRESENCE mandatory },
   ...
}

-- **************************************************************
--
-- POSITIONING MEASUREMENT UPDATE ELEMENTARY PROCEDURE
--
-- **************************************************************

-- **************************************************************
--
-- Positioning Measurement Update
--
-- **************************************************************

PositioningMeasurementUpdate ::= SEQUENCE {
   protocolIEs ProtocolIE-Container { { PositioningMeasurementUpdateIEs} },
   ...
}

PositioningMeasurementUpdateIEs F1AP-PROTOCOL-IES ::= {
   { ID id-TransactionID CRITICALITY reject TYPE TransactionID PRESENCE mandatory }|
   { ID id-LMF-MeasurementID CRITICALITY reject TYPE LMF-MeasurementID PRESENCE mandatory }|
   { ID id-RAN-MeasurementID CRITICALITY reject TYPE RAN-MeasurementID PRESENCE mandatory }|
   { ID id-SRSConfiguration CRITICALITY ignore TYPE SRSConfiguration PRESENCE optional},
   ...
}

-- **************************************************************
--
-- TRP INFORMATION EXCHANGE ELEMENTARY PROCEDURE
--
-- **************************************************************

-- **************************************************************
--
-- TRP Information Request
--
-- **************************************************************

TRPInformationRequest ::= SEQUENCE {
   protocolIEs ProtocolIE-Container { { TRPInformationRequestIEs} },
   ...
}

TRPInformationRequestIEs F1AP-PROTOCOL-IES ::= {
   { ID id-TransactionID CRITICALITY reject TYPE TransactionID PRESENCE mandatory }|
   { ID id-TRPList CRITICALITY ignore TYPE TRPList PRESENCE optional }|
   { ID id-TRPInformationTypeListTRPReq CRITICALITY reject TYPE TRPInformationTypeListTRPReq PRESENCE mandatory },
   ...
}

TRPInformationTypeListTRPReq ::= SEQUENCE (SIZE(1.. maxnoofTRPInfoTypes)) OF ProtocolIE-SingleContainer { { TRPInformationTypeItemTRPReq } }

TRPInformationTypeItemTRPReq F1AP-PROTOCOL-IES ::= {
   { ID id-TRPInformationTypeItem CRITICALITY reject TYPE TRPInformationTypeItem PRESENCE mandatory },
   ...
}

-- **************************************************************
--
-- TRP Information Response
--
-- **************************************************************

TRPInformationResponse ::= SEQUENCE {
   protocolIEs ProtocolIE-Container { { TRPInformationResponseIEs} },
   ...
}

TRPInformationResponseIEs F1AP-PROTOCOL-IES ::= {
   { ID id-TransactionID CRITICALITY reject TYPE TransactionID PRESENCE mandatory }|
   { ID id-TRPInformationListTRPResp CRITICALITY ignore TYPE TRPInformationListTRPResp PRESENCE mandatory }|
   { ID id-CriticalityDiagnostics CRITICALITY ignore TYPE CriticalityDiagnostics PRESENCE optional },
   ...
}

TRPInformationListTRPResp ::= SEQUENCE (SIZE(1.. maxnoofTRPs)) OF ProtocolIE-SingleContainer { { TRPInformationItemTRPResp } }

TRPInformationItemTRPResp F1AP-PROTOCOL-IES ::= {
   { ID id-TRPInformationItem CRITICALITY ignore TYPE TRPInformationItem PRESENCE mandatory },
   ...
}

-- **************************************************************
--
-- TRP Information Failure
--
-- **************************************************************

TRPInformationFailure ::= SEQUENCE {
   protocolIEs ProtocolIE-Container { { TRPInformationFailureIEs} },
   ...
}

TRPInformationFailureIEs F1AP-PROTOCOL-IES ::= {
   { ID id-TransactionID CRITICALITY reject TYPE TransactionID PRESENCE mandatory }|
   { ID id-Cause CRITICALITY ignore TYPE Cause PRESENCE mandatory }|
   { ID id-CriticalityDiagnostics CRITICALITY ignore TYPE CriticalityDiagnostics PRESENCE optional },
   ...
}

-- **************************************************************
--
-- POSITIONING INFORMATION EXCHANGE ELEMENTARY PROCEDURE
--
-- **************************************************************

-- **************************************************************
--
-- Positioning Information Request
--
-- **************************************************************

PositioningInformationRequest ::= SEQUENCE {
   protocolIEs ProtocolIE-Container { { PositioningInformationRequestIEs} },
   ...
}

PositioningInformationRequestIEs F1AP-PROTOCOL-IES ::= {
   { ID id-gNB-CU-UE-F1AP-ID CRITICALITY reject TYPE GNB-CU-UE-F1AP-ID PRESENCE mandatory }|
   { ID id-gNB-DU-UE-F1AP-ID CRITICALITY reject TYPE GNB-DU-UE-F1AP-ID PRESENCE mandatory }|
   { ID id-RequestedSRSTransmissionCharacteristics CRITICALITY ignore TYPE RequestedSRSTransmissionCharacteristics PRESENCE optional},
   ...
}

-- **************************************************************
--
-- Positioning Information Response
--
-- **************************************************************

PositioningInformationResponse ::= SEQUENCE {
   protocolIEs ProtocolIE-Container { { PositioningInformationResponseIEs} },
   ...
}

PositioningInformationResponseIEs F1AP-PROTOCOL-IES ::= {
   { ID id-gNB-CU-UE-F1AP-ID CRITICALITY reject TYPE GNB-CU-UE-F1AP-ID PRESENCE mandatory }|
   { ID id-gNB-DU-UE-F1AP-ID CRITICALITY reject TYPE GNB-DU-UE-F1AP-ID PRESENCE mandatory }|
   { ID id-SRSConfiguration CRITICALITY ignore TYPE SRSConfiguration PRESENCE optional}|
   { ID id-SFNInitialisationTime CRITICALITY ignore TYPE RelativeTime1900 PRESENCE optional}|
   { ID id-CriticalityDiagnostics CRITICALITY ignore TYPE CriticalityDiagnostics PRESENCE optional },
   ...
}

-- **************************************************************
--
-- Positioning Information Failure
--
-- **************************************************************

PositioningInformationFailure ::= SEQUENCE {
   protocolIEs ProtocolIE-Container { { PositioningInformationFailureIEs} },
   ...
}

PositioningInformationFailureIEs F1AP-PROTOCOL-IES ::= {

   { ID id-gNB-CU-UE-F1AP-ID CRITICALITY reject TYPE GNB-CU-UE-F1AP-ID PRESENCE mandatory }|
   { ID id-gNB-DU-UE-F1AP-ID CRITICALITY reject TYPE GNB-DU-UE-F1AP-ID PRESENCE mandatory }|
   { ID id-Cause CRITICALITY ignore TYPE Cause PRESENCE mandatory }|
   { ID id-CriticalityDiagnostics CRITICALITY ignore TYPE CriticalityDiagnostics PRESENCE optional },
   ...
}

-- **************************************************************
--
-- POSITIONING ACTIVATION PROCEDURE
--
-- **************************************************************

-- **************************************************************
--
-- Positioning Activation Request
--
-- **************************************************************

PositioningActivationRequest ::= SEQUENCE {
   protocolIEs ProtocolIE-Container { { PositioningActivationRequestIEs} },
   ...
}

PositioningActivationRequestIEs F1AP-PROTOCOL-IES ::= {
   { ID id-gNB-CU-UE-F1AP-ID CRITICALITY reject TYPE GNB-CU-UE-F1AP-ID PRESENCE mandatory }|
   { ID id-gNB-DU-UE-F1AP-ID CRITICALITY reject TYPE GNB-DU-UE-F1AP-ID PRESENCE mandatory }|
   { ID id-SRSType CRITICALITY reject TYPE SRSType PRESENCE mandatory }|
   { ID id-ActivationTime CRITICALITY ignore TYPE RelativeTime1900 PRESENCE optional },
   ...
}

SRSType ::= CHOICE {
   semipersistentSRS SemipersistentSRS,
   aperiodicSRS AperiodicSRS,
   choice-extension ProtocolIE-SingleContainer { { SRSType-ExtIEs} }
}

SRSType-ExtIEs F1AP-PROTOCOL-IES ::= {
   ...
}

SemipersistentSRS ::= SEQUENCE {
   sRSResourceSetID SRSResourceSetID,
   sRSSpatialRelation SpatialRelationInfo OPTIONAL,
   iE-Extensions ProtocolExtensionContainer { {SemipersistentSRS-ExtIEs} } OPTIONAL,
   ...
}

SemipersistentSRS-ExtIEs F1AP-PROTOCOL-EXTENSION ::= {
   { ID id-SRSSpatialRelationPerSRSResource CRITICALITY ignore EXTENSION SpatialRelationPerSRSResource PRESENCE optional},
   ...
}

AperiodicSRS ::= SEQUENCE {
   aperiodic ENUMERATED {true, ...},
   sRSResourceTrigger SRSResourceTrigger OPTIONAL,
   iE-Extensions ProtocolExtensionContainer { {AperiodicSRS-ExtIEs} } OPTIONAL,
   ...
}

AperiodicSRS-ExtIEs F1AP-PROTOCOL-EXTENSION ::= {
   ...
}

-- **************************************************************
--
-- Positioning Activation Response
--
-- **************************************************************

PositioningActivationResponse ::= SEQUENCE {
   protocolIEs ProtocolIE-Container { { PositioningActivationResponseIEs} },
   ...
}

PositioningActivationResponseIEs F1AP-PROTOCOL-IES ::= {
   { ID id-gNB-CU-UE-F1AP-ID CRITICALITY reject TYPE GNB-CU-UE-F1AP-ID PRESENCE mandatory }|
   { ID id-gNB-DU-UE-F1AP-ID CRITICALITY reject TYPE GNB-DU-UE-F1AP-ID PRESENCE mandatory }|
   { ID id-SystemFrameNumber CRITICALITY ignore TYPE SystemFrameNumber PRESENCE optional }|
   { ID id-SlotNumber CRITICALITY ignore TYPE SlotNumber PRESENCE optional }|
   { ID id-CriticalityDiagnostics CRITICALITY ignore TYPE CriticalityDiagnostics PRESENCE optional },
   ...
}

-- **************************************************************
--
-- Positioning Activation Failure
--
-- **************************************************************

PositioningActivationFailure ::= SEQUENCE {
   protocolIEs ProtocolIE-Container { { PositioningActivationFailureIEs} },
   ...
}

PositioningActivationFailureIEs F1AP-PROTOCOL-IES ::= {
   { ID id-gNB-CU-UE-F1AP-ID CRITICALITY reject TYPE GNB-CU-UE-F1AP-ID PRESENCE mandatory }|
   { ID id-gNB-DU-UE-F1AP-ID CRITICALITY reject TYPE GNB-DU-UE-F1AP-ID PRESENCE mandatory }|
   { ID id-Cause CRITICALITY ignore TYPE Cause PRESENCE mandatory }|
   { ID id-CriticalityDiagnostics CRITICALITY ignore TYPE CriticalityDiagnostics PRESENCE optional },
   ...
}

-- **************************************************************
--
-- POSITIONING DEACTIVATION PROCEDURE
--
-- **************************************************************

-- **************************************************************
--
-- Positioning Deactivation
--
-- **************************************************************

PositioningDeactivation ::= SEQUENCE {
   protocolIEs ProtocolIE-Container { { PositioningDeactivationIEs} },
   ...
}

PositioningDeactivationIEs F1AP-PROTOCOL-IES ::= {
   { ID id-gNB-CU-UE-F1AP-ID CRITICALITY reject TYPE GNB-CU-UE-F1AP-ID PRESENCE mandatory }|
   { ID id-gNB-DU-UE-F1AP-ID CRITICALITY reject TYPE GNB-DU-UE-F1AP-ID PRESENCE mandatory }|
   { ID id-AbortTransmission CRITICALITY ignore TYPE AbortTransmission PRESENCE mandatory },
   ...
}

-- **************************************************************
--
-- POSITIONING INFORMATION UPDATE PROCEDURE
--
-- **************************************************************

-- **************************************************************
--
-- Positioning Information Update
--
-- **************************************************************

PositioningInformationUpdate ::= SEQUENCE {
   protocolIEs ProtocolIE-Container { { PositioningInformationUpdateIEs} },
   ...
}

PositioningInformationUpdateIEs F1AP-PROTOCOL-IES ::= {
   { ID id-gNB-CU-UE-F1AP-ID CRITICALITY reject TYPE GNB-CU-UE-F1AP-ID PRESENCE mandatory }|
   { ID id-gNB-DU-UE-F1AP-ID CRITICALITY reject TYPE GNB-DU-UE-F1AP-ID PRESENCE mandatory }|
   { ID id-SRSConfiguration CRITICALITY ignore TYPE SRSConfiguration PRESENCE optional}|
   { ID id-SFNInitialisationTime CRITICALITY ignore TYPE RelativeTime1900 PRESENCE optional},
   ...
}

-- **************************************************************
--
-- E-CID MEASUREMENT PROCEDURE
--
-- **************************************************************

-- **************************************************************
--
-- E-CID Measurement Initiation Request
--
-- **************************************************************

E-CIDMeasurementInitiationRequest ::= SEQUENCE {
   protocolIEs ProtocolIE-Container {{E-CIDMeasurementInitiationRequest-IEs}},
   ...
}

E-CIDMeasurementInitiationRequest-IEs F1AP-PROTOCOL-IES ::= {
   { ID id-gNB-CU-UE-F1AP-ID CRITICALITY reject TYPE GNB-CU-UE-F1AP-ID PRESENCE mandatory }|
   { ID id-gNB-DU-UE-F1AP-ID CRITICALITY reject TYPE GNB-DU-UE-F1AP-ID PRESENCE mandatory }|
   { ID id-LMF-UE-MeasurementID CRITICALITY reject TYPE LMF-UE-MeasurementID PRESENCE mandatory }|
   { ID id-RAN-UE-MeasurementID CRITICALITY reject TYPE RAN-UE-MeasurementID PRESENCE mandatory }|
   { ID id-E-CID-ReportCharacteristics CRITICALITY reject TYPE E-CID-ReportCharacteristics PRESENCE mandatory }|
   { ID id-E-CID-MeasurementPeriodicity CRITICALITY reject TYPE MeasurementPeriodicity PRESENCE conditional }|
   -- The above IE shall be present if the E-CID-ReportCharacteristics IE is set to “periodic” –-
   { ID id-E-CID-MeasurementQuantities CRITICALITY reject TYPE E-CID-MeasurementQuantities PRESENCE mandatory},
   ...
}

-- **************************************************************
--
-- E-CID Measurement Initiation Response
--
-- **************************************************************

E-CIDMeasurementInitiationResponse ::= SEQUENCE {
   protocolIEs ProtocolIE-Container {{E-CIDMeasurementInitiationResponse-IEs}},
   ...
}

E-CIDMeasurementInitiationResponse-IEs F1AP-PROTOCOL-IES ::= {
   { ID id-gNB-CU-UE-F1AP-ID CRITICALITY reject TYPE GNB-CU-UE-F1AP-ID PRESENCE mandatory }|
   { ID id-gNB-DU-UE-F1AP-ID CRITICALITY reject TYPE GNB-DU-UE-F1AP-ID PRESENCE mandatory }|
   { ID id-LMF-UE-MeasurementID CRITICALITY reject TYPE LMF-UE-MeasurementID PRESENCE mandatory }|
   { ID id-RAN-UE-MeasurementID CRITICALITY reject TYPE RAN-UE-MeasurementID PRESENCE mandatory }|
   { ID id-E-CID-MeasurementResult CRITICALITY ignore TYPE E-CID-MeasurementResult PRESENCE optional}|
   { ID id-Cell-Portion-ID CRITICALITY ignore TYPE Cell-Portion-ID PRESENCE optional}|
   { ID id-CriticalityDiagnostics CRITICALITY ignore TYPE CriticalityDiagnostics PRESENCE optional},
   ...
}

-- **************************************************************
--
-- E-CID Measurement Initiation Failure
--
-- **************************************************************

E-CIDMeasurementInitiationFailure ::= SEQUENCE {
   protocolIEs ProtocolIE-Container {{E-CIDMeasurementInitiationFailure-IEs}},
   ...
}

E-CIDMeasurementInitiationFailure-IEs F1AP-PROTOCOL-IES ::= {
   { ID id-gNB-CU-UE-F1AP-ID CRITICALITY reject TYPE GNB-CU-UE-F1AP-ID PRESENCE mandatory }|
   { ID id-gNB-DU-UE-F1AP-ID CRITICALITY reject TYPE GNB-DU-UE-F1AP-ID PRESENCE mandatory }|
   { ID id-LMF-UE-MeasurementID CRITICALITY reject TYPE LMF-UE-MeasurementID PRESENCE mandatory }|
   { ID id-RAN-UE-MeasurementID CRITICALITY reject TYPE RAN-UE-MeasurementID PRESENCE mandatory }|
   { ID id-Cause CRITICALITY ignore TYPE Cause PRESENCE mandatory }|
   { ID id-CriticalityDiagnostics CRITICALITY ignore TYPE CriticalityDiagnostics PRESENCE optional},
   ...
}

-- **************************************************************
--
-- E-CID MEASUREMENT FAILURE INDICATION PROCEDURE
--
-- **************************************************************

-- **************************************************************
--
-- E-CID Measurement Failure Indication
--
-- **************************************************************

E-CIDMeasurementFailureIndication ::= SEQUENCE {
   protocolIEs ProtocolIE-Container {{E-CIDMeasurementFailureIndication-IEs}},
   ...
}

E-CIDMeasurementFailureIndication-IEs F1AP-PROTOCOL-IES ::= {
   { ID id-gNB-CU-UE-F1AP-ID CRITICALITY reject TYPE GNB-CU-UE-F1AP-ID PRESENCE mandatory }|
   { ID id-gNB-DU-UE-F1AP-ID CRITICALITY reject TYPE GNB-DU-UE-F1AP-ID PRESENCE mandatory }|
   { ID id-LMF-UE-MeasurementID CRITICALITY reject TYPE LMF-UE-MeasurementID PRESENCE mandatory }|
   { ID id-RAN-UE-MeasurementID CRITICALITY reject TYPE RAN-UE-MeasurementID PRESENCE mandatory }|
   { ID id-Cause CRITICALITY ignore TYPE Cause PRESENCE mandatory},
   ...
}

-- **************************************************************
--
-- E-CID MEASUREMENT REPORT PROCEDURE
--
-- **************************************************************

-- **************************************************************
--
-- E-CID Measurement Report
--
-- **************************************************************

E-CIDMeasurementReport ::= SEQUENCE {
   protocolIEs ProtocolIE-Container {{E-CIDMeasurementReport-IEs}},
   ...
}

E-CIDMeasurementReport-IEs F1AP-PROTOCOL-IES ::= {
   { ID id-gNB-CU-UE-F1AP-ID CRITICALITY reject TYPE GNB-CU-UE-F1AP-ID PRESENCE mandatory }|
   { ID id-gNB-DU-UE-F1AP-ID CRITICALITY reject TYPE GNB-DU-UE-F1AP-ID PRESENCE mandatory }|
   { ID id-LMF-UE-MeasurementID CRITICALITY reject TYPE LMF-UE-MeasurementID PRESENCE mandatory }|
   { ID id-RAN-UE-MeasurementID CRITICALITY reject TYPE RAN-UE-MeasurementID PRESENCE mandatory }|
   { ID id-E-CID-MeasurementResult CRITICALITY ignore TYPE E-CID-MeasurementResult PRESENCE mandatory }|
   { ID id-Cell-Portion-ID CRITICALITY ignore TYPE Cell-Portion-ID PRESENCE optional},

   ...
}

-- **************************************************************
--
-- E-CID MEASUREMENT TERMINATION PROCEDURE
--
-- **************************************************************

-- **************************************************************
--
-- E-CID Measurement Termination Command
--
-- **************************************************************

E-CIDMeasurementTerminationCommand ::= SEQUENCE {
   protocolIEs ProtocolIE-Container {{E-CIDMeasurementTerminationCommand-IEs}},
   ...
}

E-CIDMeasurementTerminationCommand-IEs F1AP-PROTOCOL-IES ::= {
   { ID id-gNB-CU-UE-F1AP-ID CRITICALITY reject TYPE GNB-CU-UE-F1AP-ID PRESENCE mandatory }|
   { ID id-gNB-DU-UE-F1AP-ID CRITICALITY reject TYPE GNB-DU-UE-F1AP-ID PRESENCE mandatory }|
   { ID id-LMF-UE-MeasurementID CRITICALITY reject TYPE LMF-UE-MeasurementID PRESENCE mandatory }|
   { ID id-RAN-UE-MeasurementID CRITICALITY reject TYPE RAN-UE-MeasurementID PRESENCE mandatory },
   ...
}

END
-- ASN1STOP

-- ASN1START
-- **************************************************************
--
-- Information Element Definitions
--
-- **************************************************************

F1AP-IEs {
   itu-t (0) identified-organization (4) etsi (0) mobileDomain (0)
ngran-access (22) modules (3) f1ap (3) version1 (1) f1ap-IEs (2) }

DEFINITIONS AUTOMATIC TAGS ::=

BEGIN

IMPORTS
id-gNB-CUSystemInformation,
id-HandoverPreparationInformation,
id-TAISliceSupportList,
id-RANAC,
id-BearerTypeChange,
id-Cell-Direction,
id-Cell-Type,
id-CellGroupConfig,
id-AvailablePLMNList,
id-PDUSessionID,
id-ULPDUSessionAggregateMaximumBitRate,
id-DC-Based-Duplication-Configured,
id-DC-Based-Duplication-Activation,
id-Duplication-Activation,
id-DLPDCPSNLength,
id-ULPDCPSNLength,
id-RLC-Status,
id-MeasurementTimingConfiguration,
id-DRB-Information,
id-QoSFlowMappingIndication,
id-ServingCellMO,
id-RLCMode,
id-ExtendedServedPLMNs-List,
id-ExtendedAvailablePLMN-List,
id-DRX-LongCycleStartOffset,
id-SelectedBandCombinationIndex,
id-SelectedFeatureSetEntryIndex,
id-Ph-InfoSCG,
id-latest-RRC-Version-Enhanced,
id-RequestedBandCombinationIndex,
id-RequestedFeatureSetEntryIndex,
id-DRX-Config,
id-UEAssistanceInformation,
id-PDCCH-BlindDetectionSCG,
id-Requested-PDCCH-BlindDetectionSCG,
id-BPLMN-ID-Info-List,
id-NotificationInformation,
id-TNLAssociationTransportLayerAddressgNBDU,
id-portNumber,
id-AdditionalSIBMessageList,
id-IgnorePRACHConfiguration,
id-CG-Config,
id-Ph-InfoMCG,
id-AggressorgNBSetID,
id-VictimgNBSetID,
id-MeasGapSharingConfig,
id-systemInformationAreaID,
id-areaScope,
id-IntendedTDD-DL-ULConfig,
id-QosMonitoringRequest,
id-BHInfo,
id-IAB-Info-IAB-DU,
id-IAB-Info-IAB-donor-CU,
id-IAB-Barred,
id-SIB12-message,
id-SIB13-message,
id-SIB14-message,
id-UEAssistanceInformationEUTRA,
id-SL-PHY-MAC-RLC-Config,
id-SL-ConfigDedicatedEUTRA-Info,
id-AlternativeQoSParaSetList,
id-CurrentQoSParaSetIndex,
id-CarrierList,
id-ULCarrierList,
id-FrequencyShift7p5khz,
id-SSB-PositionsInBurst,
id-NRPRACHConfig,
id-TDD-UL-DLConfigCommonNR,
id-CNPacketDelayBudgetDownlink,
id-CNPacketDelayBudgetUplink,
id-ExtendedPacketDelayBudget,
id-TSCTrafficCharacteristics,
id-AdditionalPDCPDuplicationTNL-List,
id-RLCDuplicationInformation,
id-AdditionalDuplicationIndication,
id-mdtConfiguration,
id-TraceCollectionEntityURI,
id-NID,
id-NPNSupportInfo,
id-NPNBroadcastInformation,
id-AvailableSNPN-ID-List,
id-SIB10-message,
id-RequestedP-MaxFR2,
id-DLCarrierList,
id-ExtendedTAISliceSupportList,
id-E-CID-MeasurementQuantities-Item,
id-ConfiguredTACIndication,
id-NRCGI,
id-SFN-Offset,
id-TransmissionStopIndicator,
id-SrsFrequency,
id-EstimatedArrivalProbability,
id-TRPType,
id-SRSSpatialRelationPerSRSResource,
maxNRARFCN,
maxnoofErrors,
maxnoofBPLMNs,
maxnoofBPLMNsNR,
maxnoofDLUPTNLInformation,
maxnoofNrCellBands,
maxnoofULUPTNLInformation,
maxnoofQoSFlows,
maxnoofSliceItems,
maxnoofSIBTypes,
maxnoofSITypes,
maxCellineNB,
maxnoofExtendedBPLMNs,
maxnoofAdditionalSIBs,
maxnoofUACPLMNs,
maxnoofUACperPLMN,
maxCellingNBDU,
maxnoofTLAs,
maxnoofGTPTLAs,
maxnoofslots,
maxnoofNonUPTrafficMappings,
maxnoofServingCells,
maxnoofServedCellsIAB,
maxnoofChildIABNodes,
maxnoofIABSTCInfo,
maxnoofSymbols,
maxnoofDUFSlots,
maxnoofHSNASlots,
maxnoofEgressLinks,
maxnoofMappingEntries,
maxnoofDSInfo,
maxnoofQoSParaSets,
maxnoofPC5QoSFlows,
maxnoofSSBAreas,
maxnoofNRSCSs,
maxnoofPhysicalResourceBlocks,
maxnoofPhysicalResourceBlocks-1,
maxnoofPRACHconfigs,
maxnoofRACHReports,
maxnoofRLFReports,
maxnoofAdditionalPDCPDuplicationTNL,
maxnoofRLCDuplicationState,
maxnoofCHOcells,
maxnoofMDTPLMNs,
maxnoofCAGsupported,
maxnoofNIDsupported,
maxnoofExtSliceItems,
maxnoofPosMeas,
maxnoofTRPInfoTypes,
maxnoofSRSTriggerStates,
maxnoofSpatialRelations,
maxnoBcastCell,
maxnoofTRPs,
maxnoofAngleInfo,
maxnooflcs-gcs-translation,
maxnoofPath,
maxnoofMeasE-CID,
maxnoofSSBs,
maxnoSRS-ResourceSets,
maxnoSRS-ResourcePerSet,
maxnoSRS-Carriers,
maxnoSCSs,
maxnoSRS-Resources,
maxnoSRS-PosResources,
maxnoSRS-PosResourceSets,
maxnoSRS-PosResourcePerSet,
maxnoofPRS-ResourceSets,
maxnoofPRS-ResourcesPerSet,
maxNoOfMeasTRPs,
maxnoofPRSresourceSets,
maxnoofPRSresources

FROM F1AP-Constants

Criticality,
ProcedureCode,
ProtocolIE-ID,
TriggeringMessage

FROM F1AP-CommonDataTypes

ProtocolExtensionContainer{},
F1AP-PROTOCOL-EXTENSION,
ProtocolIE-SingleContainer{},
F1AP-PROTOCOL-IES

FROM F1AP-Containers;

-- A

AbortTransmission ::= CHOICE {
   sRSResourceSetID SRSResourceSetID,
   releaseALL NULL,
   choice-extension ProtocolIE-SingleContainer { { AbortTransmission-ExtIEs } }
}

AbortTransmission-ExtIEs F1AP-PROTOCOL-IES ::= {
   ...
}

AccessPointPosition ::= SEQUENCE {
   latitudeSign ENUMERATED {north, south},
   latitude INTEGER (0..8388607),
   longitude INTEGER (-8388608..8388607),
   directionOfAltitude ENUMERATED {height, depth},
   altitude INTEGER (0..32767),
   uncertaintySemi-major INTEGER (0..127),
   uncertaintySemi-minor INTEGER (0..127),
   orientationOfMajorAxis INTEGER (0..179),
   uncertaintyAltitude INTEGER (0..127),
   confidence INTEGER (0..100),
   iE-Extensions ProtocolExtensionContainer { { AccessPointPosition-ExtIEs} } OPTIONAL
}

AccessPointPosition-ExtIEs F1AP-PROTOCOL-EXTENSION ::= {
   ...
}

Activated-Cells-to-be-Updated-List ::= SEQUENCE (SIZE(1..maxnoofServedCellsIAB)) OF Activated-Cells-to-be-Updated-List-Item

Activated-Cells-to-be-Updated-List-Item ::= SEQUENCE{
   nRCGI NRCGI,
   iAB-DU-Cell-Resource-Configuration-Mode-Info IAB-DU-Cell-Resource-Configuration-Mode-Info,
   iE-Extensions ProtocolExtensionContainer { { Activated-Cells-to-be-Updated-List-Item-ExtIEs} } OPTIONAL
}

Activated-Cells-to-be-Updated-List-Item-ExtIEs F1AP-PROTOCOL-EXTENSION ::= {
   ...
}

ActiveULBWP ::= SEQUENCE {
   locationAndBandwidth INTEGER (0..37949,...),
   subcarrierSpacing ENUMERATED {kHz15, kHz30, kHz60, kHz120,...},
   cyclicPrefix ENUMERATED {normal, extended},
   txDirectCurrentLocation INTEGER (0..3301,...),
   shift7dot5kHz ENUMERATED {true, ...} OPTIONAL,
   sRSConfig SRSConfig,
   iE-Extensions ProtocolExtensionContainer { { ActiveULBWP-ExtIEs} } OPTIONAL
}

ActiveULBWP-ExtIEs F1AP-PROTOCOL-EXTENSION ::= {
   ...
}

AdditionalDuplicationIndication ::= ENUMERATED {
   three,
   four,
   ...
}

AdditionalPath-List::= SEQUENCE (SIZE(1..maxnoofPath)) OF AdditionalPath-Item

AdditionalPath-Item ::=SEQUENCE {
   relativePathDelay RelativePathDelay,
   pathQuality TRPMeasurementQuality OPTIONAL,
   iE-Extensions ProtocolExtensionContainer { { AdditionalPath-Item-ExtIEs } } OPTIONAL
}

AdditionalPath-Item-ExtIEs F1AP-PROTOCOL-EXTENSION ::= {
   ...
}

AdditionalPDCPDuplicationTNL-List ::= SEQUENCE (SIZE(1..maxnoofAdditionalPDCPDuplicationTNL)) OF AdditionalPDCPDuplicationTNL-Item

AdditionalPDCPDuplicationTNL-Item ::=SEQUENCE {
   additionalPDCPDuplicationUPTNLInformation UPTransportLayerInformation,
   iE-Extensions ProtocolExtensionContainer { { AdditionalPDCPDuplicationTNL-ItemExtIEs } } OPTIONAL,
   ...
}

AdditionalPDCPDuplicationTNL-ItemExtIEs F1AP-PROTOCOL-EXTENSION ::= {
   { ID id-BHInfo CRITICALITY ignore EXTENSION BHInfo PRESENCE optional },
   ...
}

AdditionalSIBMessageList ::= SEQUENCE (SIZE(1..maxnoofAdditionalSIBs)) OF AdditionalSIBMessageList-Item

AdditionalSIBMessageList-Item ::= SEQUENCE {
   additionalSIB OCTET STRING,
   iE-Extensions ProtocolExtensionContainer { { AdditionalSIBMessageList-Item-ExtIEs} } OPTIONAL
}

AdditionalSIBMessageList-Item-ExtIEs F1AP-PROTOCOL-EXTENSION ::= {
   ...
}

AdditionalRRMPriorityIndex ::= BIT STRING (SIZE(32))

AggressorCellList ::= SEQUENCE (SIZE(1..maxCellingNBDU)) OF AggressorCellList-Item

AggressorCellList-Item ::= SEQUENCE {
   aggressorCell-ID NRCGI,
   iE-Extensions ProtocolExtensionContainer { { AggressorCellList-Item-ExtIEs } } OPTIONAL
}

AggressorCellList-Item-ExtIEs F1AP-PROTOCOL-EXTENSION ::= {
   ...
}

AggressorgNBSetID ::= SEQUENCE {
   aggressorgNBSetID GNBSetID,
   iE-Extensions ProtocolExtensionContainer { { AggressorgNBSetID-ExtIEs } } OPTIONAL
}

AggressorgNBSetID-ExtIEs F1AP-PROTOCOL-EXTENSION ::= {
   ...
}

AllocationAndRetentionPriority ::= SEQUENCE {
   priorityLevel PriorityLevel,
   pre-emptionCapability Pre-emptionCapability,
   pre-emptionVulnerability Pre-emptionVulnerability,
   iE-Extensions ProtocolExtensionContainer { {AllocationAndRetentionPriority-ExtIEs} } OPTIONAL,
   ...
}

AllocationAndRetentionPriority-ExtIEs F1AP-PROTOCOL-EXTENSION ::= {
   ...
}

AlternativeQoSParaSetList ::= SEQUENCE (SIZE(1..maxnoofQoSParaSets)) OF AlternativeQoSParaSetItem

AlternativeQoSParaSetItem ::= SEQUENCE {
   alternativeQoSParaSetIndex QoSParaSetIndex,
   guaranteedFlowBitRateDL BitRate OPTIONAL,
   guaranteedFlowBitRateUL BitRate OPTIONAL,
   packetDelayBudget PacketDelayBudget OPTIONAL,
   packetErrorRate PacketErrorRate OPTIONAL,
   iE-Extensions ProtocolExtensionContainer { {AlternativeQoSParaSetItem-ExtIEs} } OPTIONAL,
   ...
}

AlternativeQoSParaSetItem-ExtIEs F1AP-PROTOCOL-EXTENSION ::= {
   ...
}

AngleMeasurementQuality ::= SEQUENCE {
   azimuthQuality INTEGER(0..255),
   zenithQuality INTEGER(0..255) OPTIONAL,
   resolution ENUMERATED{deg0dot1,...},
   iE-Extensions ProtocolExtensionContainer { { AngleMeasurementQuality-ExtIEs } } OPTIONAL
}

AngleMeasurementQuality-ExtIEs F1AP-PROTOCOL-EXTENSION ::= {
   ...
}

AperiodicSRSResourceTriggerList ::= SEQUENCE (SIZE(1..maxnoofSRSTriggerStates)) OF AperiodicSRSResourceTrigger

AperiodicSRSResourceTrigger ::= INTEGER (1..3)

Associated-SCell-Item ::= SEQUENCE {
   sCell-ID NRCGI,
   iE-Extensions ProtocolExtensionContainer { { Associated-SCell-ItemExtIEs } } OPTIONAL
}

Associated-SCell-ItemExtIEs F1AP-PROTOCOL-EXTENSION ::= {
   ...
}

AvailablePLMNList ::= SEQUENCE (SIZE(1..maxnoofBPLMNs)) OF AvailablePLMNList-Item

AvailablePLMNList-Item ::= SEQUENCE {
   pLMNIdentity PLMN-Identity,
   iE-Extensions ProtocolExtensionContainer { { AvailablePLMNList-Item-ExtIEs} } OPTIONAL
}

AvailablePLMNList-Item-ExtIEs F1AP-PROTOCOL-EXTENSION ::= {
   ...
}

AvailableSNPN-ID-List ::= SEQUENCE (SIZE(1..maxnoofNIDsupported)) OF AvailableSNPN-ID-List-Item

AvailableSNPN-ID-List-Item ::= SEQUENCE {
   pLMN-Identity PLMN-Identity,
   availableNIDList BroadcastNIDList,
   iE-Extensions ProtocolExtensionContainer { { AvailableSNPN-ID-List-ItemExtIEs} } OPTIONAL,
   ...
}

AvailableSNPN-ID-List-ItemExtIEs F1AP-PROTOCOL-EXTENSION ::= {
   ...
}

AveragingWindow ::= INTEGER (0..4095, ...)

AreaScope ::= ENUMERATED {true, ...}

-- B

BandwidthSRS ::= CHOICE {
   fR1 FR1-Bandwidth,
   fR2 FR2-Bandwidth,
   choice-extension ProtocolIE-SingleContainer {{ BandwidthSRS-ExtIEs }}
}

BandwidthSRS-ExtIEs F1AP-PROTOCOL-IES ::= {
   ...
}

BAPAddress ::= BIT STRING (SIZE(10))

BAPCtrlPDUChannel ::= ENUMERATED {true, ...}

BAPlayerBHRLCchannelMappingInfo ::= SEQUENCE {
   bAPlayerBHRLCchannelMappingInfoToAdd BAPlayerBHRLCchannelMappingInfoList OPTIONAL,
   bAPlayerBHRLCchannelMappingInfoToRemove MappingInformationtoRemove OPTIONAL,
   iE-Extensions ProtocolExtensionContainer { { BAPlayerBHRLCchannelMappingInfo-ExtIEs} } OPTIONAL,
   ...
}

BAPlayerBHRLCchannelMappingInfo-ExtIEs F1AP-PROTOCOL-EXTENSION ::= {
   ...
}

BAPlayerBHRLCchannelMappingInfoList ::= SEQUENCE (SIZE(1..maxnoofMappingEntries)) OF BAPlayerBHRLCchannelMappingInfo-Item

BAPlayerBHRLCchannelMappingInfo-Item ::= SEQUENCE {
   mappingInformationIndex MappingInformationIndex,
   priorHopBAPAddress BAPAddress OPTIONAL,
   ingressbHRLCChannelID BHRLCChannelID OPTIONAL,
   nextHopBAPAddress BAPAddress OPTIONAL,
   egressbHRLCChannelID BHRLCChannelID OPTIONAL,
   iE-Extensions ProtocolExtensionContainer { { BAPlayerBHRLCchannelMappingInfo-ItemExtIEs} } OPTIONAL,
   ...
}

BAPlayerBHRLCchannelMappingInfo-ItemExtIEs F1AP-PROTOCOL-EXTENSION ::= {
   ...
}

BAPPathID ::= BIT STRING (SIZE(10))

BAPRoutingID ::= SEQUENCE {
   bAPAddress BAPAddress,
   bAPPathID BAPPathID,
   iE-Extensions ProtocolExtensionContainer { { BAPRoutingIDExtIEs } } OPTIONAL
}

BAPRoutingIDExtIEs F1AP-PROTOCOL-EXTENSION ::= {
   ...
}

BitRate ::= INTEGER (0..4000000000000,...)

BearerTypeChange ::= ENUMERATED {true, ...}

BHRLCChannelID ::= BIT STRING (SIZE(16))

BHChannels-FailedToBeModified-Item ::= SEQUENCE {
   bHRLCChannelID BHRLCChannelID,
   cause Cause OPTIONAL,
   iE-Extensions ProtocolExtensionContainer { { BHChannels-FailedToBeModified-ItemExtIEs } } OPTIONAL
}

BHChannels-FailedToBeModified-ItemExtIEs F1AP-PROTOCOL-EXTENSION ::= {
   ...
}

BHChannels-FailedToBeSetup-Item ::= SEQUENCE {
   bHRLCChannelID BHRLCChannelID,
   cause Cause OPTIONAL,
   iE-Extensions ProtocolExtensionContainer { { BHChannels-FailedToBeSetup-ItemExtIEs } } OPTIONAL
}

BHChannels-FailedToBeSetup-ItemExtIEs F1AP-PROTOCOL-EXTENSION ::= {
   ...
}

BHChannels-FailedToBeSetupMod-Item ::= SEQUENCE {
   bHRLCChannelID BHRLCChannelID,
   cause Cause OPTIONAL ,
   iE-Extensions ProtocolExtensionContainer { { BHChannels-FailedToBeSetupMod-ItemExtIEs } } OPTIONAL
}

BHChannels-FailedToBeSetupMod-ItemExtIEs F1AP-PROTOCOL-EXTENSION ::= {
   ...
}

BHChannels-Modified-Item ::= SEQUENCE {
   bHRLCChannelID BHRLCChannelID,
   iE-Extensions ProtocolExtensionContainer { { BHChannels-Modified-ItemExtIEs } } OPTIONAL
}

BHChannels-Modified-ItemExtIEs F1AP-PROTOCOL-EXTENSION ::= {
   ...
}

BHChannels-Required-ToBeReleased-Item ::= SEQUENCE {
   bHRLCChannelID BHRLCChannelID,
   iE-Extensions ProtocolExtensionContainer { { BHChannels-Required-ToBeReleased-ItemExtIEs } } OPTIONAL
}

BHChannels-Required-ToBeReleased-ItemExtIEs F1AP-PROTOCOL-EXTENSION ::= {
   ...
}

BHChannels-Setup-Item ::= SEQUENCE {
   bHRLCChannelID BHRLCChannelID,
   iE-Extensions ProtocolExtensionContainer { { BHChannels-Setup-ItemExtIEs } } OPTIONAL
}

BHChannels-Setup-ItemExtIEs F1AP-PROTOCOL-EXTENSION ::= {
   ...
}

BHChannels-SetupMod-Item ::= SEQUENCE {
   bHRLCChannelID BHRLCChannelID,
   iE-Extensions ProtocolExtensionContainer { { BHChannels-SetupMod-ItemExtIEs } } OPTIONAL
}

BHChannels-SetupMod-ItemExtIEs F1AP-PROTOCOL-EXTENSION ::= {
   ...
}

BHChannels-ToBeModified-Item ::= SEQUENCE {
   bHRLCChannelID BHRLCChannelID,
   bHQoSInformation BHQoSInformation,
   rLCmode RLCMode OPTIONAL,
   bAPCtrlPDUChannel BAPCtrlPDUChannel OPTIONAL,
   trafficMappingInfo TrafficMappingInfo OPTIONAL,
   iE-Extensions ProtocolExtensionContainer { { BHChannels-ToBeModified-ItemExtIEs } } OPTIONAL
}

BHChannels-ToBeModified-ItemExtIEs F1AP-PROTOCOL-EXTENSION ::= {
   ...
}

BHChannels-ToBeReleased-Item ::= SEQUENCE {
   bHRLCChannelID BHRLCChannelID,
   iE-Extensions ProtocolExtensionContainer { { BHChannels-ToBeReleased-ItemExtIEs } } OPTIONAL
}

BHChannels-ToBeReleased-ItemExtIEs F1AP-PROTOCOL-EXTENSION ::= {
   ...
}

BHChannels-ToBeSetup-Item ::= SEQUENCE {
   bHRLCChannelID BHRLCChannelID,
   bHQoSInformation BHQoSInformation,
   rLCmode RLCMode,
   bAPCtrlPDUChannel BAPCtrlPDUChannel OPTIONAL,
   trafficMappingInfo TrafficMappingInfo OPTIONAL,
   iE-Extensions ProtocolExtensionContainer { { BHChannels-ToBeSetup-ItemExtIEs } } OPTIONAL
}

BHChannels-ToBeSetup-ItemExtIEs F1AP-PROTOCOL-EXTENSION ::= {
   ...
}

BHChannels-ToBeSetupMod-Item ::= SEQUENCE {
   bHRLCChannelID BHRLCChannelID,
   bHQoSInformation BHQoSInformation,
   rLCmode RLCMode,
   bAPCtrlPDUChannel BAPCtrlPDUChannel OPTIONAL,
   trafficMappingInfo TrafficMappingInfo OPTIONAL,
   iE-Extensions ProtocolExtensionContainer { { BHChannels-ToBeSetupMod-ItemExtIEs } } OPTIONAL
}

BHChannels-ToBeSetupMod-ItemExtIEs F1AP-PROTOCOL-EXTENSION ::= {
   ...
}

BHInfo ::= SEQUENCE {
   bAProutingID BAPRoutingID OPTIONAL,
   egressBHRLCCHList EgressBHRLCCHList OPTIONAL,
   iE-Extensions ProtocolExtensionContainer { { BHInfo-ExtIEs} } OPTIONAL
}

BHInfo-ExtIEs F1AP-PROTOCOL-EXTENSION ::= {
   ...
}

BHQoSInformation ::= CHOICE {
   bHRLCCHQoS QoSFlowLevelQoSParameters,
   eUTRANBHRLCCHQoS EUTRANQoS,
   cPTrafficType CPTrafficType,
   choice-extension ProtocolIE-SingleContainer { { BHQoSInformation-ExtIEs} }
}

BHQoSInformation-ExtIEs F1AP-PROTOCOL-IES ::= {
   ...
}

BH-Routing-Information-Added-List-Item ::= SEQUENCE {
   bAPRoutingID BAPRoutingID,
   nextHopBAPAddress BAPAddress,
   iE-Extensions ProtocolExtensionContainer { { BH-Routing-Information-Added-List-ItemExtIEs} } OPTIONAL
}

BH-Routing-Information-Added-List-ItemExtIEs F1AP-PROTOCOL-EXTENSION ::= {
   ...
}

BH-Routing-Information-Removed-List-Item ::= SEQUENCE {
   bAPRoutingID BAPRoutingID,
   iE-Extensions ProtocolExtensionContainer { { BH-Routing-Information-Removed-List-ItemExtIEs} } OPTIONAL
}

BH-Routing-Information-Removed-List-ItemExtIEs F1AP-PROTOCOL-EXTENSION ::= {
   ...
}

BPLMN-ID-Info-List ::= SEQUENCE (SIZE(1..maxnoofBPLMNsNR)) OF BPLMN-ID-Info-Item

BPLMN-ID-Info-Item ::= SEQUENCE {
   pLMN-Identity-List AvailablePLMNList,
   extended-PLMN-Identity-List ExtendedAvailablePLMN-List OPTIONAL,
   fiveGS-TAC FiveGS-TAC OPTIONAL,
   nr-cell-ID NRCellIdentity,
   ranac RANAC OPTIONAL,
   iE-Extensions ProtocolExtensionContainer { { BPLMN-ID-Info-ItemExtIEs} } OPTIONAL,
   ...
}

BPLMN-ID-Info-ItemExtIEs F1AP-PROTOCOL-EXTENSION ::= {
   { ID id-ConfiguredTACIndication CRITICALITY ignore EXTENSION ConfiguredTACIndication PRESENCE optional }|
   { ID id-NPNBroadcastInformation CRITICALITY reject EXTENSION NPNBroadcastInformation PRESENCE optional},
   ...
}

ServedPLMNs-List ::= SEQUENCE (SIZE(1..maxnoofBPLMNs)) OF ServedPLMNs-Item

ServedPLMNs-Item ::= SEQUENCE {
   pLMN-Identity PLMN-Identity,
   iE-Extensions ProtocolExtensionContainer { { ServedPLMNs-ItemExtIEs} } OPTIONAL,
   ...
}

ServedPLMNs-ItemExtIEs F1AP-PROTOCOL-EXTENSION ::= {
   { ID id-TAISliceSupportList CRITICALITY ignore EXTENSION SliceSupportList PRESENCE optional }|
   { ID id-NPNSupportInfo CRITICALITY reject EXTENSION NPNSupportInfo PRESENCE optional }|
   { ID id-ExtendedTAISliceSupportList CRITICALITY reject EXTENSION ExtendedSliceSupportList PRESENCE optional },
   ...
}

BroadcastCAGList ::= SEQUENCE (SIZE(1..maxnoofCAGsupported)) OF CAGID

BroadcastNIDList ::= SEQUENCE (SIZE(1..maxnoofNIDsupported)) OF NID

BroadcastSNPN-ID-List ::= SEQUENCE (SIZE(1..maxnoofNIDsupported)) OF BroadcastSNPN-ID-List-Item

BroadcastSNPN-ID-List-Item ::= SEQUENCE {
   pLMN-Identity PLMN-Identity,
   broadcastNIDList BroadcastNIDList,
   iE-Extensions ProtocolExtensionContainer { { BroadcastSNPN-ID-List-ItemExtIEs} } OPTIONAL,
   ...
}

BroadcastSNPN-ID-List-ItemExtIEs F1AP-PROTOCOL-EXTENSION ::= {
   ...
}

BroadcastPNI-NPN-ID-List ::= SEQUENCE (SIZE(1..maxnoofCAGsupported)) OF BroadcastPNI-NPN-ID-List-Item

BroadcastPNI-NPN-ID-List-Item ::= SEQUENCE {
   pLMN-Identity PLMN-Identity,
   broadcastCAGList BroadcastCAGList,
   iE-Extensions ProtocolExtensionContainer { { BroadcastPNI-NPN-ID-List-ItemExtIEs} } OPTIONAL,
   ...
}

BroadcastPNI-NPN-ID-List-ItemExtIEs F1AP-PROTOCOL-EXTENSION ::= {
   ...
}
BurstArrivalTime ::= OCTET STRING

-- C
CAGID ::= BIT STRING (SIZE(32))

Cancel-all-Warning-Messages-Indicator ::= ENUMERATED {true, ...}

Candidate-SpCell-Item ::= SEQUENCE {
   candidate-SpCell-ID NRCGI ,
   iE-Extensions ProtocolExtensionContainer { { Candidate-SpCell-ItemExtIEs } } OPTIONAL,
   ...
}

Candidate-SpCell-ItemExtIEs F1AP-PROTOCOL-EXTENSION ::= {
   ...
}

CapacityValue::= SEQUENCE {
   capacityValue INTEGER (0..100),
   sSBAreaCapacityValueList SSBAreaCapacityValueList OPTIONAL,
   iE-Extensions ProtocolExtensionContainer { { CapacityValue-ExtIEs} } OPTIONAL
}

CapacityValue-ExtIEs F1AP-PROTOCOL-EXTENSION ::= {
   ...
}

Cause ::= CHOICE {
   radioNetwork CauseRadioNetwork,
   transport CauseTransport,
   protocol CauseProtocol,
   misc CauseMisc,
   choice-extension ProtocolIE-SingleContainer { { Cause-ExtIEs} }
}

Cause-ExtIEs F1AP-PROTOCOL-IES ::= {
   ...
}

CauseMisc ::= ENUMERATED {
   control-processing-overload,
   not-enough-user-plane-processing-resources,
   hardware-failure,
   om-intervention,
   unspecified,
   ...
}

CauseProtocol ::= ENUMERATED {
   transfer-syntax-error,
   abstract-syntax-error-reject,
   abstract-syntax-error-ignore-and-notify,
   message-not-compatible-with-receiver-state,
   semantic-error,
   abstract-syntax-error-falsely-constructed-message,
   unspecified,
   ...
}

CauseRadioNetwork ::= ENUMERATED {
   unspecified,
   rl-failure-rlc,
   unknown-or-already-allocated-gnb-cu-ue-f1ap-id,
   unknown-or-already-allocated-gnb-du-ue-f1ap-id,
   unknown-or-inconsistent-pair-of-ue-f1ap-id,
   interaction-with-other-procedure,
   not-supported-qci-Value,
   action-desirable-for-radio-reasons,
   no-radio-resources-available,
   procedure-cancelled,
   normal-release,
   ...,
   cell-not-available,
   rl-failure-others,
   ue-rejection,
   resources-not-available-for-the-slice,
   amf-initiated-abnormal-release,
   release-due-to-pre-emption,
   plmn-not-served-by-the-gNB-CU,
   multiple-drb-id-instances,
   unknown-drb-id,
   multiple-bh-rlc-ch-id-instances,
   unknown-bh-rlc-ch-id,
   cho-cpc-resources-tobechanged,
   nPN-not-supported,
   nPN-access-denied,
   gNB-CU-Cell-Capacity-Exceeded,
   report-characteristics-empty,
   existing-measurement-ID,
   measurement-temporarily-not-available,
   measurement-not-supported-for-the-object,
   unknown-bh-address,
   unknown-bap-routing-id,
   insufficient-ue-capabilities

}

CauseTransport ::= ENUMERATED {
   unspecified,
   transport-resource-unavailable,
   ...,
   unknown-TNL-address-for-IAB,
   unknown-UP-TNL-information-for-IAB
}

CellGroupConfig ::= OCTET STRING

CellCapacityClassValue ::= INTEGER (1..100,...)

Cell-Direction ::= ENUMERATED {dl-only, ul-only}

CellMeasurementResultList ::= SEQUENCE (SIZE(1.. maxCellingNBDU)) OF CellMeasurementResultItem

CellMeasurementResultItem ::= SEQUENCE {
   cellID NRCGI,
   radioResourceStatus RadioResourceStatus OPTIONAL,
   compositeAvailableCapacityGroup CompositeAvailableCapacityGroup OPTIONAL,
   sliceAvailableCapacity SliceAvailableCapacity OPTIONAL,
   numberofActiveUEs NumberofActiveUEs OPTIONAL,
   iE-Extensions ProtocolExtensionContainer { { CellMeasurementResultItem-ExtIEs} } OPTIONAL
}

CellMeasurementResultItem-ExtIEs F1AP-PROTOCOL-EXTENSION ::= {
   ...
}

Cell-Portion-ID ::= INTEGER (0..4095,...)

Cells-Failed-to-be-Activated-List-Item ::= SEQUENCE {
   nRCGI NRCGI,
   cause Cause,
   iE-Extensions ProtocolExtensionContainer { { Cells-Failed-to-be-Activated-List-ItemExtIEs } } OPTIONAL,
   ...
}

Cells-Failed-to-be-Activated-List-ItemExtIEs F1AP-PROTOCOL-EXTENSION ::= {
   ...
}

Cells-Status-Item ::= SEQUENCE {
   nRCGI NRCGI,
   service-status Service-Status,
   iE-Extensions ProtocolExtensionContainer { { Cells-Status-ItemExtIEs } } OPTIONAL,
   ...
}

Cells-Status-ItemExtIEs F1AP-PROTOCOL-EXTENSION ::= {
   ...
}

Cells-To-Be-Broadcast-Item ::= SEQUENCE {
   nRCGI NRCGI,
   iE-Extensions ProtocolExtensionContainer { { Cells-To-Be-Broadcast-ItemExtIEs } } OPTIONAL,
   ...
}

Cells-To-Be-Broadcast-ItemExtIEs F1AP-PROTOCOL-EXTENSION ::= {
   ...
}

Cells-Broadcast-Completed-Item ::= SEQUENCE {
   nRCGI NRCGI,
   iE-Extensions ProtocolExtensionContainer { { Cells-Broadcast-Completed-ItemExtIEs } } OPTIONAL,
   ...
}

Cells-Broadcast-Completed-ItemExtIEs F1AP-PROTOCOL-EXTENSION ::= {
   ...
}

Broadcast-To-Be-Cancelled-Item ::= SEQUENCE {
   nRCGI NRCGI,
   iE-Extensions ProtocolExtensionContainer { { Broadcast-To-Be-Cancelled-ItemExtIEs } } OPTIONAL,
   ...
}

Broadcast-To-Be-Cancelled-ItemExtIEs F1AP-PROTOCOL-EXTENSION ::= {
   ...
}

Cells-Broadcast-Cancelled-Item ::= SEQUENCE {
   nRCGI NRCGI,
   numberOfBroadcasts NumberOfBroadcasts,
   iE-Extensions ProtocolExtensionContainer { { Cells-Broadcast-Cancelled-ItemExtIEs } } OPTIONAL,
   ...
}

Cells-Broadcast-Cancelled-ItemExtIEs F1AP-PROTOCOL-EXTENSION ::= {
   ...
}

Cells-to-be-Activated-List-Item ::= SEQUENCE {
   nRCGI NRCGI,
   nRPCI NRPCI OPTIONAL,
   iE-Extensions ProtocolExtensionContainer { { Cells-to-be-Activated-List-ItemExtIEs} } OPTIONAL,
   ...
}

Cells-to-be-Activated-List-ItemExtIEs F1AP-PROTOCOL-EXTENSION ::= {
   { ID id-gNB-CUSystemInformation CRITICALITY reject EXTENSION GNB-CUSystemInformation PRESENCE optional }|
   { ID id-AvailablePLMNList CRITICALITY ignore EXTENSION AvailablePLMNList PRESENCE optional }|
   { ID id-ExtendedAvailablePLMN-List CRITICALITY ignore EXTENSION ExtendedAvailablePLMN-List PRESENCE optional }|
   { ID id-IAB-Info-IAB-donor-CU CRITICALITY ignore EXTENSION IAB-Info-IAB-donor-CU PRESENCE optional}|
   { ID id-AvailableSNPN-ID-List CRITICALITY ignore EXTENSION AvailableSNPN-ID-List PRESENCE optional },
   ...
}

Cells-to-be-Deactivated-List-Item ::= SEQUENCE {
   nRCGI NRCGI ,
   iE-Extensions ProtocolExtensionContainer { { Cells-to-be-Deactivated-List-ItemExtIEs } } OPTIONAL,
   ...
}

Cells-to-be-Deactivated-List-ItemExtIEs F1AP-PROTOCOL-EXTENSION ::= {
   ...
}

Cells-to-be-Barred-Item::= SEQUENCE {
   nRCGI NRCGI ,
   cellBarred CellBarred,
   iE-Extensions ProtocolExtensionContainer { { Cells-to-be-Barred-Item-ExtIEs } } OPTIONAL
}

Cells-to-be-Barred-Item-ExtIEs F1AP-PROTOCOL-EXTENSION ::= {
   { ID id-IAB-Barred CRITICALITY ignore EXTENSION IAB-Barred PRESENCE optional },

   ...
}

CellBarred ::= ENUMERATED {barred, not-barred, ...}

CellSize ::= ENUMERATED {verysmall, small, medium, large, ...}

CellToReportList ::= SEQUENCE (SIZE(1.. maxCellingNBDU)) OF CellToReportItem

CellToReportItem ::= SEQUENCE {
   cellID NRCGI,
   sSBToReportList SSBToReportList OPTIONAL,
   sliceToReportList SliceToReportList OPTIONAL,
   iE-Extensions ProtocolExtensionContainer { { CellToReportItem-ExtIEs} } OPTIONAL
}

CellToReportItem-ExtIEs F1AP-PROTOCOL-EXTENSION ::= {
   ...
}

CellType ::= SEQUENCE {
   cellSize CellSize,
   iE-Extensions ProtocolExtensionContainer { {CellType-ExtIEs} } OPTIONAL,
   ...
}

CellType-ExtIEs F1AP-PROTOCOL-EXTENSION ::= {
   ...
}

CellULConfigured ::= ENUMERATED {none, ul, sul, ul-and-sul, ...}

Child-Node-Cells-List ::= SEQUENCE (SIZE(1..maxnoofChildIABNodes)) OF Child-Node-Cells-List-Item

Child-Node-Cells-List-Item ::= SEQUENCE{
   nRCGI NRCGI,
   iAB-DU-Cell-Resource-Configuration-Mode-Info IAB-DU-Cell-Resource-Configuration-Mode-Info OPTIONAL,
   iAB-STC-Info IAB-STC-Info OPTIONAL,
   rACH-Config-Common RACH-Config-Common OPTIONAL,
   rACH-Config-Common-IAB RACH-Config-Common-IAB OPTIONAL,
   cSI-RS-Configuration OCTET STRING OPTIONAL,
   sR-Configuration OCTET STRING OPTIONAL,
   pDCCH-ConfigSIB1 OCTET STRING OPTIONAL,
   sCS-Common OCTET STRING OPTIONAL,
   multiplexingInfo MultiplexingInfo OPTIONAL,
   iE-Extensions ProtocolExtensionContainer {{Child-Node-Cells-List-Item-ExtIEs}} OPTIONAL
}

Child-Node-Cells-List-Item-ExtIEs F1AP-PROTOCOL-EXTENSION ::= {
   ...
}

Child-Nodes-List ::= SEQUENCE (SIZE(1..maxnoofChildIABNodes)) OF Child-Nodes-List-Item

Child-Nodes-List-Item ::= SEQUENCE{
   gNB-CU-UE-F1AP-ID GNB-CU-UE-F1AP-ID,
   gNB-DU-UE-F1AP-ID GNB-DU-UE-F1AP-ID,
   child-Node-Cells-List Child-Node-Cells-List OPTIONAL,
   iE-Extensions ProtocolExtensionContainer {{Child-Nodes-List-Item-ExtIEs}} OPTIONAL
}

Child-Nodes-List-Item-ExtIEs F1AP-PROTOCOL-EXTENSION ::= {
   ...
}

CHOtrigger-InterDU ::= ENUMERATED {
   cho-initiation,
   cho-replace,
   ...
}

CHOtrigger-IntraDU ::= ENUMERATED {
   cho-initiation,
   cho-replace,
   cho-cancel,
   ...
}

CNUEPagingIdentity ::= CHOICE {
   fiveG-S-TMSI BIT STRING (SIZE(48)),
   choice-extension ProtocolIE-SingleContainer { { CNUEPagingIdentity-ExtIEs } }
}

CNUEPagingIdentity-ExtIEs F1AP-PROTOCOL-IES ::= {
   ...
}

CompositeAvailableCapacityGroup ::= SEQUENCE {
   compositeAvailableCapacityDownlink CompositeAvailableCapacity,
   compositeAvailableCapacityUplink CompositeAvailableCapacity,
   iE-Extensions ProtocolExtensionContainer { { CompositeAvailableCapacityGroup-ExtIEs} } OPTIONAL
}

CompositeAvailableCapacityGroup-ExtIEs F1AP-PROTOCOL-EXTENSION ::= {
   ...
}

CompositeAvailableCapacity ::= SEQUENCE {
   cellCapacityClassValue CellCapacityClassValue OPTIONAL,
   capacityValue CapacityValue,
   iE-Extensions ProtocolExtensionContainer { { CompositeAvailableCapacity-ExtIEs} } OPTIONAL
}

CompositeAvailableCapacity-ExtIEs F1AP-PROTOCOL-EXTENSION ::= {
   ...
}

CHO-Probability ::= INTEGER (1..100)

ConditionalInterDUMobilityInformation ::= SEQUENCE {
   cho-trigger CHOtrigger-InterDU,
   targetgNB-DUUEF1APID GNB-DU-UE-F1AP-ID OPTIONAL
   -- This IE shall be present if the cho-trigger IE is present and set to "cho-replace" --,
   iE-Extensions ProtocolExtensionContainer { { ConditionalInterDUMobilityInformation-ExtIEs} } OPTIONAL,
   ...
}

ConditionalInterDUMobilityInformation-ExtIEs F1AP-PROTOCOL-EXTENSION ::={
   { ID id-EstimatedArrivalProbability CRITICALITY ignore EXTENSION CHO-Probability PRESENCE optional },
   ...
}

ConditionalIntraDUMobilityInformation ::= SEQUENCE {
   cho-trigger CHOtrigger-IntraDU,
   targetCellsTocancel TargetCellList OPTIONAL,
   -- This IE may be present if the cho-trigger IE is present and set to "cho-cancel"
   iE-Extensions ProtocolExtensionContainer { { ConditionalIntraDUMobilityInformation-ExtIEs} } OPTIONAL,
   ...
}

ConditionalIntraDUMobilityInformation-ExtIEs F1AP-PROTOCOL-EXTENSION ::={
   { ID id-EstimatedArrivalProbability CRITICALITY ignore EXTENSION CHO-Probability PRESENCE optional },
   ...
}

ConfiguredTACIndication ::= ENUMERATED {
   true,
   ...
}

CoordinateID ::= INTEGER (0..511, ...)

CP-TransportLayerAddress ::= CHOICE {
   endpoint-IP-address TransportLayerAddress,
   endpoint-IP-address-and-port Endpoint-IP-address-and-port,
   choice-extension ProtocolIE-SingleContainer { { CP-TransportLayerAddress-ExtIEs } }
}

CP-TransportLayerAddress-ExtIEs F1AP-PROTOCOL-IES ::= {
   ...
}

CPTrafficType ::= INTEGER (1..3,...)

CriticalityDiagnostics ::= SEQUENCE {
   procedureCode ProcedureCode OPTIONAL,
   triggeringMessage TriggeringMessage OPTIONAL,
   procedureCriticality Criticality OPTIONAL,
   transactionID TransactionID OPTIONAL,
   iEsCriticalityDiagnostics CriticalityDiagnostics-IE-List OPTIONAL,
   iE-Extensions ProtocolExtensionContainer {{CriticalityDiagnostics-ExtIEs}} OPTIONAL,
   ...
}

CriticalityDiagnostics-ExtIEs F1AP-PROTOCOL-EXTENSION ::= {
   ...
}

CriticalityDiagnostics-IE-List ::= SEQUENCE (SIZE (1.. maxnoofErrors)) OF CriticalityDiagnostics-IE-Item

CriticalityDiagnostics-IE-Item ::= SEQUENCE {
   iECriticality Criticality,
   iE-ID ProtocolIE-ID,
   typeOfError TypeOfError,
   iE-Extensions ProtocolExtensionContainer {{CriticalityDiagnostics-IE-Item-ExtIEs}} OPTIONAL,
   ...
}

CriticalityDiagnostics-IE-Item-ExtIEs F1AP-PROTOCOL-EXTENSION ::= {
   ...
}

C-RNTI ::= INTEGER (0..65535, ...)

CUDURadioInformationType ::= CHOICE {
   rIM CUDURIMInformation,
   choice-extension ProtocolIE-SingleContainer { { CUDURadioInformationType-ExtIEs} }
}

CUDURadioInformationType-ExtIEs F1AP-PROTOCOL-IES ::= {
   ...
}

CUDURIMInformation ::= SEQUENCE {
   victimgNBSetID GNBSetID,
   rIMRSDetectionStatus RIMRSDetectionStatus,
   iE-Extensions ProtocolExtensionContainer { { CUDURIMInformation-ExtIEs} } OPTIONAL
}

CUDURIMInformation-ExtIEs F1AP-PROTOCOL-EXTENSION ::= {
   ...
}

CUtoDURRCInformation ::= SEQUENCE {
   cG-ConfigInfo CG-ConfigInfo OPTIONAL,
   uE-CapabilityRAT-ContainerList UE-CapabilityRAT-ContainerList OPTIONAL,
   measConfig MeasConfig OPTIONAL,
   iE-Extensions ProtocolExtensionContainer { { CUtoDURRCInformation-ExtIEs} } OPTIONAL,
   ...
}

CUtoDURRCInformation-ExtIEs F1AP-PROTOCOL-EXTENSION ::= {
   { ID id-HandoverPreparationInformation CRITICALITY ignore EXTENSION HandoverPreparationInformation PRESENCE optional }|
   { ID id-CellGroupConfig CRITICALITY ignore EXTENSION CellGroupConfig PRESENCE optional }|
   { ID id-MeasurementTimingConfiguration CRITICALITY ignore EXTENSION MeasurementTimingConfiguration PRESENCE optional }|
   { ID id-UEAssistanceInformation CRITICALITY ignore EXTENSION UEAssistanceInformation PRESENCE optional }|
   { ID id-CG-Config CRITICALITY ignore EXTENSION CG-Config PRESENCE optional }|
   { ID id-UEAssistanceInformationEUTRA CRITICALITY ignore EXTENSION UEAssistanceInformationEUTRA PRESENCE optional },
   ...
}

-- D

DCBasedDuplicationConfigured::= ENUMERATED{true,..., false}

Dedicated-SIDelivery-NeededUE-Item ::= SEQUENCE {
   gNB-CU-UE-F1AP-ID GNB-CU-UE-F1AP-ID,
   nRCGI NRCGI,
   iE-Extensions ProtocolExtensionContainer { { DedicatedSIDeliveryNeededUE-Item-ExtIEs} } OPTIONAL,
   ...
}

DedicatedSIDeliveryNeededUE-Item-ExtIEs F1AP-PROTOCOL-EXTENSION::={
   ...
}

DL-PRS ::= SEQUENCE {
   prsid INTEGER (0..255),
   dl-PRSResourceSetID PRS-Resource-Set-ID,
   dl-PRSResourceID PRS-Resource-ID OPTIONAL,
   iE-Extensions ProtocolExtensionContainer { {DL-PRS-ExtIEs} } OPTIONAL
}

DL-PRS-ExtIEs F1AP-PROTOCOL-EXTENSION ::= {
   ...
}

DL-PRSMutingPattern ::= CHOICE {
   two BIT STRING (SIZE(2)),
   four BIT STRING (SIZE(4)),
   six BIT STRING (SIZE(6)),
   eight BIT STRING (SIZE(8)),
   sixteen BIT STRING (SIZE(16)),
   thirty-two BIT STRING (SIZE(32)),
   choice-extension ProtocolIE-SingleContainer { { DL-PRSMutingPattern-ExtIEs } }
}

DL-PRSMutingPattern-ExtIEs F1AP-PROTOCOL-IES ::= {
   ...
}

DLPRSResourceCoordinates ::= SEQUENCE {
   listofDL-PRSResourceSetARP SEQUENCE (SIZE(1.. maxnoofPRS-ResourceSets)) OF DLPRSResourceSetARP,
   iE-Extensions ProtocolExtensionContainer { { DLPRSResourceCoordinates-ExtIEs } } OPTIONAL
}

DLPRSResourceCoordinates-ExtIEs F1AP-PROTOCOL-EXTENSION ::= {
   ...
}

DLPRSResourceSetARP ::= SEQUENCE {
   dl-PRSResourceSetID PRS-Resource-Set-ID,
   dL-PRSResourceSetARPLocation DL-PRSResourceSetARPLocation,
   listofDL-PRSResourceARP SEQUENCE (SIZE(1.. maxnoofPRS-ResourcesPerSet)) OF DLPRSResourceARP,
   iE-Extensions ProtocolExtensionContainer { { DLPRSResourceSetARP-ExtIEs } } OPTIONAL
}

DLPRSResourceSetARP-ExtIEs F1AP-PROTOCOL-EXTENSION ::= {
   ...
}

DL-PRSResourceSetARPLocation ::= CHOICE {
   relativeGeodeticLocation RelativeGeodeticLocation,
   relativeCartesianLocation RelativeCartesianLocation,
   choice-Extension ProtocolIE-SingleContainer { { DL-PRSResourceSetARPLocation-ExtIEs } }
}

DL-PRSResourceSetARPLocation-ExtIEs F1AP-PROTOCOL-IES ::= {
   ...
}

DLPRSResourceARP ::= SEQUENCE {
   dl-PRSResourceID PRS-Resource-ID,
   dL-PRSResourceARPLocation DL-PRSResourceARPLocation,
   iE-Extensions ProtocolExtensionContainer { { DLPRSResourceARP-ExtIEs } } OPTIONAL
}

DLPRSResourceARP-ExtIEs F1AP-PROTOCOL-EXTENSION ::= {
   ...
}

DL-PRSResourceARPLocation ::= CHOICE {
   relativeGeodeticLocation RelativeGeodeticLocation,
   relativeCartesianLocation RelativeCartesianLocation,
   choice-Extension ProtocolIE-SingleContainer { { DL-PRSResourceARPLocation-ExtIEs } }
}

DL-PRSResourceARPLocation-ExtIEs F1AP-PROTOCOL-IES ::= {
   ...
}

DL-UP-TNL-Address-to-Update-List-Item ::= SEQUENCE {
   oldIPAdress TransportLayerAddress,
   newIPAdress TransportLayerAddress,
   iE-Extensions ProtocolExtensionContainer { { DL-UP-TNL-Address-to-Update-List-ItemExtIEs } } OPTIONAL,
   ...
}

DL-UP-TNL-Address-to-Update-List-ItemExtIEs F1AP-PROTOCOL-EXTENSION ::= {
   ...
}

DLUPTNLInformation-ToBeSetup-List ::= SEQUENCE (SIZE(1..maxnoofDLUPTNLInformation)) OF DLUPTNLInformation-ToBeSetup-Item

DLUPTNLInformation-ToBeSetup-Item ::= SEQUENCE {
   dLUPTNLInformation UPTransportLayerInformation ,
   iE-Extensions ProtocolExtensionContainer { { DLUPTNLInformation-ToBeSetup-ItemExtIEs } } OPTIONAL,
   ...
}

DLUPTNLInformation-ToBeSetup-ItemExtIEs F1AP-PROTOCOL-EXTENSION ::= {
   ...
}

DRB-Activity-Item ::= SEQUENCE {
   dRBID DRBID,
   dRB-Activity DRB-Activity OPTIONAL,
   iE-Extensions ProtocolExtensionContainer { { DRB-Activity-ItemExtIEs } } OPTIONAL,
   ...
}

DRB-Activity-ItemExtIEs F1AP-PROTOCOL-EXTENSION ::= {
   ...
}

DRB-Activity ::= ENUMERATED {active, not-active}

DRBID ::= INTEGER (1..32, ...)

DRBs-FailedToBeModified-Item ::= SEQUENCE {
   dRBID DRBID ,
   cause Cause OPTIONAL,
   iE-Extensions ProtocolExtensionContainer { { DRBs-FailedToBeModified-ItemExtIEs } } OPTIONAL,
   ...
}

DRBs-FailedToBeModified-ItemExtIEs F1AP-PROTOCOL-EXTENSION ::= {
   ...
}

DRBs-FailedToBeSetup-Item ::= SEQUENCE {
   dRBID DRBID,
   cause Cause OPTIONAL,
   iE-Extensions ProtocolExtensionContainer { { DRBs-FailedToBeSetup-ItemExtIEs } } OPTIONAL,
   ...
}

DRBs-FailedToBeSetup-ItemExtIEs F1AP-PROTOCOL-EXTENSION ::= {
   ...
}

DRBs-FailedToBeSetupMod-Item ::= SEQUENCE {
   dRBID DRBID ,
   cause Cause OPTIONAL ,
   iE-Extensions ProtocolExtensionContainer { { DRBs-FailedToBeSetupMod-ItemExtIEs } } OPTIONAL,
   ...
}

DRBs-FailedToBeSetupMod-ItemExtIEs F1AP-PROTOCOL-EXTENSION ::= {
   ...
}

DRB-Information ::= SEQUENCE {
   dRB-QoS QoSFlowLevelQoSParameters,
   sNSSAI SNSSAI,
   notificationControl NotificationControl OPTIONAL,
   flows-Mapped-To-DRB-List Flows-Mapped-To-DRB-List,
   iE-Extensions ProtocolExtensionContainer { { DRB-Information-ItemExtIEs } } OPTIONAL
}

DRB-Information-ItemExtIEs F1AP-PROTOCOL-EXTENSION ::= {
   ...
}

DRBs-Modified-Item ::= SEQUENCE {
   dRBID DRBID,
   lCID LCID OPTIONAL,
   dLUPTNLInformation-ToBeSetup-List DLUPTNLInformation-ToBeSetup-List,
   iE-Extensions ProtocolExtensionContainer { { DRBs-Modified-ItemExtIEs } } OPTIONAL,
   ...
}

DRBs-Modified-ItemExtIEs F1AP-PROTOCOL-EXTENSION ::= {
   { ID id-RLC-Status CRITICALITY ignore EXTENSION RLC-Status PRESENCE optional }|
   { ID id-AdditionalPDCPDuplicationTNL-List CRITICALITY ignore EXTENSION AdditionalPDCPDuplicationTNL-List PRESENCE optional }|
   { ID id-CurrentQoSParaSetIndex CRITICALITY ignore EXTENSION QoSParaSetIndex PRESENCE optional },
   ...
}

DRBs-ModifiedConf-Item ::= SEQUENCE {
   dRBID DRBID,
   uLUPTNLInformation-ToBeSetup-List ULUPTNLInformation-ToBeSetup-List ,
   iE-Extensions ProtocolExtensionContainer { { DRBs-ModifiedConf-ItemExtIEs } } OPTIONAL,
   ...
}

DRBs-ModifiedConf-ItemExtIEs F1AP-PROTOCOL-EXTENSION ::= {
   { ID id-AdditionalPDCPDuplicationTNL-List CRITICALITY ignore EXTENSION AdditionalPDCPDuplicationTNL-List PRESENCE optional },
   ...
}

DRB-Notify-Item ::= SEQUENCE {
   dRBID DRBID,
   notification-Cause Notification-Cause,
   iE-Extensions ProtocolExtensionContainer { { DRB-Notify-ItemExtIEs } } OPTIONAL,
   ...
}

DRB-Notify-ItemExtIEs F1AP-PROTOCOL-EXTENSION ::= {
   { ID id-CurrentQoSParaSetIndex CRITICALITY ignore EXTENSION QoSParaSetNotifyIndex PRESENCE optional },
   ...
}

DRBs-Required-ToBeModified-Item ::= SEQUENCE {
   dRBID DRBID,
   dLUPTNLInformation-ToBeSetup-List DLUPTNLInformation-ToBeSetup-List ,
   iE-Extensions ProtocolExtensionContainer { { DRBs-Required-ToBeModified-ItemExtIEs } } OPTIONAL,
   ...
}

DRBs-Required-ToBeModified-ItemExtIEs F1AP-PROTOCOL-EXTENSION ::= {
   { ID id-RLC-Status CRITICALITY ignore EXTENSION RLC-Status PRESENCE optional }|
   { ID id-AdditionalPDCPDuplicationTNL-List CRITICALITY ignore EXTENSION AdditionalPDCPDuplicationTNL-List PRESENCE optional },
   ...
}

DRBs-Required-ToBeReleased-Item ::= SEQUENCE {
   dRBID DRBID,
   iE-Extensions ProtocolExtensionContainer { { DRBs-Required-ToBeReleased-ItemExtIEs } } OPTIONAL,
   ...
}

DRBs-Required-ToBeReleased-ItemExtIEs F1AP-PROTOCOL-EXTENSION ::= {
   ...
}

DRBs-Setup-Item ::= SEQUENCE {
   dRBID DRBID,
   lCID LCID OPTIONAL,
   dLUPTNLInformation-ToBeSetup-List DLUPTNLInformation-ToBeSetup-List ,
   iE-Extensions ProtocolExtensionContainer { { DRBs-Setup-ItemExtIEs } } OPTIONAL,
   ...
}

DRBs-Setup-ItemExtIEs F1AP-PROTOCOL-EXTENSION ::= {
   { ID id-AdditionalPDCPDuplicationTNL-List CRITICALITY ignore EXTENSION AdditionalPDCPDuplicationTNL-List PRESENCE optional }|
   { ID id-CurrentQoSParaSetIndex CRITICALITY ignore EXTENSION QoSParaSetIndex PRESENCE optional },
   ...
}

DRBs-SetupMod-Item ::= SEQUENCE {
   dRBID DRBID,
   lCID LCID OPTIONAL,
   dLUPTNLInformation-ToBeSetup-List DLUPTNLInformation-ToBeSetup-List ,
   iE-Extensions ProtocolExtensionContainer { { DRBs-SetupMod-ItemExtIEs } } OPTIONAL,
   ...
}

DRBs-SetupMod-ItemExtIEs F1AP-PROTOCOL-EXTENSION ::= {
   { ID id-AdditionalPDCPDuplicationTNL-List CRITICALITY ignore EXTENSION AdditionalPDCPDuplicationTNL-List PRESENCE optional }|
   { ID id-CurrentQoSParaSetIndex CRITICALITY ignore EXTENSION QoSParaSetIndex PRESENCE optional },
   ...
}

DRBs-ToBeModified-Item ::= SEQUENCE {
   dRBID DRBID,
   qoSInformation QoSInformation OPTIONAL,
   uLUPTNLInformation-ToBeSetup-List ULUPTNLInformation-ToBeSetup-List ,
   uLConfiguration ULConfiguration OPTIONAL,
   iE-Extensions ProtocolExtensionContainer { { DRBs-ToBeModified-ItemExtIEs } } OPTIONAL,
   ...
}

DRBs-ToBeModified-ItemExtIEs F1AP-PROTOCOL-EXTENSION ::= {
   { ID id-DLPDCPSNLength CRITICALITY ignore EXTENSION PDCPSNLength PRESENCE optional }|
   { ID id-ULPDCPSNLength CRITICALITY ignore EXTENSION PDCPSNLength PRESENCE optional }|
   {ID id-BearerTypeChange CRITICALITY ignore EXTENSION BearerTypeChange PRESENCE optional}|
   { ID id-RLCMode CRITICALITY ignore EXTENSION RLCMode PRESENCE optional }|
   { ID id-Duplication-Activation CRITICALITY reject EXTENSION DuplicationActivation PRESENCE optional }|
   { ID id-DC-Based-Duplication-Configured CRITICALITY reject EXTENSION DCBasedDuplicationConfigured PRESENCE optional }|
   { ID id-DC-Based-Duplication-Activation CRITICALITY reject EXTENSION DuplicationActivation PRESENCE optional }|
   { ID id-AdditionalPDCPDuplicationTNL-List CRITICALITY ignore EXTENSION AdditionalPDCPDuplicationTNL-List PRESENCE optional }|
   { ID id-RLCDuplicationInformation CRITICALITY ignore EXTENSION RLCDuplicationInformation PRESENCE optional}|
   { ID id-TransmissionStopIndicator CRITICALITY ignore EXTENSION TransmissionStopIndicator PRESENCE optional},
   ...
}

DRBs-ToBeReleased-Item ::= SEQUENCE {
   dRBID DRBID,
   iE-Extensions ProtocolExtensionContainer { { DRBs-ToBeReleased-ItemExtIEs } } OPTIONAL,
   ...
}

DRBs-ToBeReleased-ItemExtIEs F1AP-PROTOCOL-EXTENSION ::= {
   ...
}

DRBs-ToBeSetup-Item ::= SEQUENCE {
   dRBID DRBID,
   qoSInformation QoSInformation,
   uLUPTNLInformation-ToBeSetup-List ULUPTNLInformation-ToBeSetup-List ,
   rLCMode RLCMode,
   uLConfiguration ULConfiguration OPTIONAL,
   duplicationActivation DuplicationActivation OPTIONAL,
   iE-Extensions ProtocolExtensionContainer { { DRBs-ToBeSetup-ItemExtIEs } } OPTIONAL,
   ...
}

DRBs-ToBeSetup-ItemExtIEs F1AP-PROTOCOL-EXTENSION ::= {
   { ID id-DC-Based-Duplication-Configured CRITICALITY reject EXTENSION DCBasedDuplicationConfigured PRESENCE optional }|
   { ID id-DC-Based-Duplication-Activation CRITICALITY reject EXTENSION DuplicationActivation PRESENCE optional }|
   { ID id-DLPDCPSNLength CRITICALITY ignore EXTENSION PDCPSNLength PRESENCE mandatory }|
   { ID id-ULPDCPSNLength CRITICALITY ignore EXTENSION PDCPSNLength PRESENCE optional }|
   { ID id-AdditionalPDCPDuplicationTNL-List CRITICALITY ignore EXTENSION AdditionalPDCPDuplicationTNL-List PRESENCE optional }|
   { ID id-RLCDuplicationInformation CRITICALITY ignore EXTENSION RLCDuplicationInformation PRESENCE optional},
   ...
}

DRBs-ToBeSetupMod-Item ::= SEQUENCE {
   dRBID DRBID,
   qoSInformation QoSInformation,
   uLUPTNLInformation-ToBeSetup-List ULUPTNLInformation-ToBeSetup-List,
   rLCMode RLCMode,
   uLConfiguration ULConfiguration OPTIONAL,
   duplicationActivation DuplicationActivation OPTIONAL,
   iE-Extensions ProtocolExtensionContainer { { DRBs-ToBeSetupMod-ItemExtIEs } } OPTIONAL,
   ...
}

DRBs-ToBeSetupMod-ItemExtIEs F1AP-PROTOCOL-EXTENSION ::= {
   { ID id-DC-Based-Duplication-Configured CRITICALITY reject EXTENSION DCBasedDuplicationConfigured PRESENCE optional }|
   { ID id-DC-Based-Duplication-Activation CRITICALITY reject EXTENSION DuplicationActivation PRESENCE optional }|
   { ID id-DLPDCPSNLength CRITICALITY ignore EXTENSION PDCPSNLength PRESENCE optional }|
   { ID id-ULPDCPSNLength CRITICALITY ignore EXTENSION PDCPSNLength PRESENCE optional }|
   { ID id-AdditionalPDCPDuplicationTNL-List CRITICALITY ignore EXTENSION AdditionalPDCPDuplicationTNL-List PRESENCE optional }|
   { ID id-RLCDuplicationInformation CRITICALITY ignore EXTENSION RLCDuplicationInformation PRESENCE optional},
   ...
}

DRXCycle ::= SEQUENCE {
   longDRXCycleLength LongDRXCycleLength,
   shortDRXCycleLength ShortDRXCycleLength OPTIONAL,
   shortDRXCycleTimer ShortDRXCycleTimer OPTIONAL,
   iE-Extensions ProtocolExtensionContainer { { DRXCycle-ExtIEs} } OPTIONAL,
   ...
}

DRXCycle-ExtIEs F1AP-PROTOCOL-EXTENSION ::= {
   ...
}

DRX-Config ::= OCTET STRING

DRXConfigurationIndicator ::= ENUMERATED{ release, ...}

DRX-LongCycleStartOffset ::= INTEGER (0..10239)

DSInformationList ::= SEQUENCE (SIZE(0..maxnoofDSInfo)) OF DSCP

DSCP ::= BIT STRING (SIZE (6))

DUtoCURRCContainer ::= OCTET STRING

DUCURadioInformationType ::= CHOICE {
   rIM DUCURIMInformation,
   choice-extension ProtocolIE-SingleContainer { { DUCURadioInformationType-ExtIEs} }
}

DUCURadioInformationType-ExtIEs F1AP-PROTOCOL-IES ::= {
   ...
}

DUCURIMInformation ::= SEQUENCE {
   victimgNBSetID GNBSetID,
   rIMRSDetectionStatus RIMRSDetectionStatus,
   aggressorCellList AggressorCellList,
   iE-Extensions ProtocolExtensionContainer { { DUCURIMInformation-ExtIEs} } OPTIONAL
}

DUCURIMInformation-ExtIEs F1AP-PROTOCOL-EXTENSION ::= {
   ...
}

DUF-Slot-Config-Item ::= CHOICE {
   explicitFormat ExplicitFormat,
   implicitFormat ImplicitFormat,
   choice-extension ProtocolIE-SingleContainer { { DUF-Slot-Config-Item-ExtIEs} }
}

DUF-Slot-Config-Item-ExtIEs F1AP-PROTOCOL-IES ::= {
   ...
}
DUF-Slot-Config-List ::= SEQUENCE (SIZE(1..maxnoofDUFSlots)) OF DUF-Slot-Config-Item

DUFSlotformatIndex ::= INTEGER(0..254)

DUFTransmissionPeriodicity ::= ENUMERATED { ms0p5, ms0p625, ms1, ms1p25, ms2, ms2p5, ms5, ms10, ...}

DU-RX-MT-RX ::= ENUMERATED {supported, not-supported}

DU-TX-MT-TX ::= ENUMERATED {supported, not-supported}

DU-RX-MT-TX ::= ENUMERATED {supported, not-supported}

DU-TX-MT-RX ::= ENUMERATED {supported, not-supported}

DUtoCURRCInformation ::= SEQUENCE {
   cellGroupConfig CellGroupConfig,
   measGapConfig MeasGapConfig OPTIONAL,
   requestedP-MaxFR1 OCTET STRING OPTIONAL,
   iE-Extensions ProtocolExtensionContainer { { DUtoCURRCInformation-ExtIEs} } OPTIONAL,
   ...
}

DUtoCURRCInformation-ExtIEs F1AP-PROTOCOL-EXTENSION ::= {
   { ID id-DRX-LongCycleStartOffset CRITICALITY ignore EXTENSION DRX-LongCycleStartOffset PRESENCE optional }|
   { ID id-SelectedBandCombinationIndex CRITICALITY ignore EXTENSION SelectedBandCombinationIndex PRESENCE optional }|
   { ID id-SelectedFeatureSetEntryIndex CRITICALITY ignore EXTENSION SelectedFeatureSetEntryIndex PRESENCE optional }|
   { ID id-Ph-InfoSCG CRITICALITY ignore EXTENSION Ph-InfoSCG PRESENCE optional }|
   { ID id-RequestedBandCombinationIndex CRITICALITY ignore EXTENSION RequestedBandCombinationIndex PRESENCE optional }|
   { ID id-RequestedFeatureSetEntryIndex CRITICALITY ignore EXTENSION RequestedFeatureSetEntryIndex PRESENCE optional }|
   { ID id-DRX-Config CRITICALITY ignore EXTENSION DRX-Config PRESENCE optional }|
   { ID id-PDCCH-BlindDetectionSCG CRITICALITY ignore EXTENSION PDCCH-BlindDetectionSCG PRESENCE optional }|
   { ID id-Requested-PDCCH-BlindDetectionSCG CRITICALITY ignore EXTENSION Requested-PDCCH-BlindDetectionSCG PRESENCE optional }|
   { ID id-Ph-InfoMCG CRITICALITY ignore EXTENSION Ph-InfoMCG PRESENCE optional }|
   { ID id-MeasGapSharingConfig CRITICALITY ignore EXTENSION MeasGapSharingConfig PRESENCE optional }|
   { ID id-SL-PHY-MAC-RLC-Config CRITICALITY ignore EXTENSION SL-PHY-MAC-RLC-Config PRESENCE optional }|
   { ID id-SL-ConfigDedicatedEUTRA-Info CRITICALITY ignore EXTENSION SL-ConfigDedicatedEUTRA-Info PRESENCE optional }|
   { ID id-RequestedP-MaxFR2 CRITICALITY ignore EXTENSION RequestedP-MaxFR2 PRESENCE optional },
   ...
}

DuplicationActivation ::= ENUMERATED{active,inactive,... }

DuplicationIndication ::= ENUMERATED {true, ... , false }

DuplicationState ::= ENUMERATED {
   active,
   inactive,
   ...
}

Dynamic5QIDescriptor ::= SEQUENCE {
   qoSPriorityLevel INTEGER (1..127),
   packetDelayBudget PacketDelayBudget,
   packetErrorRate PacketErrorRate,
   fiveQI INTEGER (0..255, ...) OPTIONAL,
   delayCritical ENUMERATED {delay-critical, non-delay-critical} OPTIONAL,
   -- C-ifGBRflow: This IE shall be present if the GBR QoS Flow Information IE is present in the QoS Flow Level QoS Parameters IE.
   averagingWindow AveragingWindow OPTIONAL,
   -- C-ifGBRflow: This IE shall be present if the GBR QoS Flow Information IE is present in the QoS Flow Level QoS Parameters IE.
   maxDataBurstVolume MaxDataBurstVolume OPTIONAL,
   iE-Extensions ProtocolExtensionContainer { { Dynamic5QIDescriptor-ExtIEs } } OPTIONAL
}

Dynamic5QIDescriptor-ExtIEs F1AP-PROTOCOL-EXTENSION ::= {
   { ID id-ExtendedPacketDelayBudget CRITICALITY ignore EXTENSION ExtendedPacketDelayBudget PRESENCE optional }|
   { ID id-CNPacketDelayBudgetDownlink CRITICALITY ignore EXTENSION ExtendedPacketDelayBudget PRESENCE optional }|
   { ID id-CNPacketDelayBudgetUplink CRITICALITY ignore EXTENSION ExtendedPacketDelayBudget PRESENCE optional },
   ...
}

DynamicPQIDescriptor ::= SEQUENCE {
   resourceType ENUMERATED {gbr, non-gbr, delay-critical-grb, ...} OPTIONAL,
   qoSPriorityLevel INTEGER (1..8, ...),
   packetDelayBudget PacketDelayBudget,
   packetErrorRate PacketErrorRate,
   averagingWindow AveragingWindow OPTIONAL,
   -- C-ifGBRflow: This IE shall be present if the GBR QoS Flow Information IE is present in the QoS Flow Level QoS Parameters IE.
   maxDataBurstVolume MaxDataBurstVolume OPTIONAL,
   iE-Extensions ProtocolExtensionContainer { { DynamicPQIDescriptor-ExtIEs } } OPTIONAL
}

DynamicPQIDescriptor-ExtIEs F1AP-PROTOCOL-EXTENSION ::= {
   ...
}

-- E

E-CID-MeasurementQuantities ::= SEQUENCE (SIZE (1.. maxnoofMeasE-CID)) OF ProtocolIE-SingleContainer { {E-CID-MeasurementQuantities-ItemIEs} }

E-CID-MeasurementQuantities-ItemIEs F1AP-PROTOCOL-IES ::= {
   { ID id-E-CID-MeasurementQuantities-Item CRITICALITY reject TYPE E-CID-MeasurementQuantities-Item PRESENCE mandatory}
}

E-CID-MeasurementQuantities-Item ::= SEQUENCE {
   e-CIDmeasurementQuantitiesValue E-CID-MeasurementQuantitiesValue,
   iE-Extensions ProtocolExtensionContainer { { E-CID-MeasurementQuantitiesValue-ExtIEs} } OPTIONAL
}

E-CID-MeasurementQuantitiesValue-ExtIEs F1AP-PROTOCOL-EXTENSION ::= {
   ...
}

E-CID-MeasurementQuantitiesValue ::= ENUMERATED {
   default,
   angleOfArrivalNR,
   ...
}

E-CID-MeasurementResult ::= SEQUENCE {
   geographicalCoordinates GeographicalCoordinates OPTIONAL,
   measuredResults-List E-CID-MeasuredResults-List OPTIONAL,
   iE-Extensions ProtocolExtensionContainer { { E-CID-MeasurementResult-ExtIEs} } OPTIONAL
}

E-CID-MeasurementResult-ExtIEs F1AP-PROTOCOL-EXTENSION ::= {
   ...
}

E-CID-MeasuredResults-List ::= SEQUENCE (SIZE(1..maxnoofMeasE-CID)) OF E-CID-MeasuredResults-Item

E-CID-MeasuredResults-Item ::= SEQUENCE {
   e-CID-MeasuredResults-Value E-CID-MeasuredResults-Value,
   iE-Extensions ProtocolExtensionContainer {{ E-CID-MeasuredResults-Item-ExtIEs }} OPTIONAL
}

E-CID-MeasuredResults-Item-ExtIEs F1AP-PROTOCOL-EXTENSION ::= {
   ...
}

E-CID-MeasuredResults-Value ::= CHOICE {
   valueAngleofArrivalNR UL-AoA,
   choice-extension ProtocolIE-SingleContainer { { E-CID-MeasuredResults-Value-ExtIEs} }
}

E-CID-MeasuredResults-Value-ExtIEs F1AP-PROTOCOL-IES ::= {
   ...
}

E-CID-ReportCharacteristics ::= ENUMERATED {
   onDemand,
   periodic,
   ...
}

EgressBHRLCCHList ::= SEQUENCE (SIZE(1..maxnoofEgressLinks)) OF EgressBHRLCCHItem

EgressBHRLCCHItem ::= SEQUENCE {
   nextHopBAPAddress BAPAddress,
   bHRLCChannelID BHRLCChannelID,
   iE-Extensions ProtocolExtensionContainer {{EgressBHRLCCHItemExtIEs }} OPTIONAL
}

EgressBHRLCCHItemExtIEs F1AP-PROTOCOL-EXTENSION ::= {
   ...
}

Endpoint-IP-address-and-port ::=SEQUENCE {
   endpointIPAddress TransportLayerAddress,
   iE-Extensions ProtocolExtensionContainer { { Endpoint-IP-address-and-port-ExtIEs} } OPTIONAL
}

Endpoint-IP-address-and-port-ExtIEs F1AP-PROTOCOL-EXTENSION ::= {
   { ID id-portNumber CRITICALITY reject EXTENSION PortNumber PRESENCE optional},
   ...
}

ExtendedAvailablePLMN-List ::= SEQUENCE (SIZE(1..maxnoofExtendedBPLMNs)) OF ExtendedAvailablePLMN-Item

ExtendedAvailablePLMN-Item ::= SEQUENCE {
   pLMNIdentity PLMN-Identity,
   iE-Extensions ProtocolExtensionContainer { { ExtendedAvailablePLMN-Item-ExtIEs} } OPTIONAL
}

ExplicitFormat ::= SEQUENCE {
   permutation Permutation,
   noofDownlinkSymbols NoofDownlinkSymbols OPTIONAL,
   noofUplinkSymbols NoofUplinkSymbols OPTIONAL,
   iE-Extensions ProtocolExtensionContainer { { ExplicitFormat-ExtIEs} } OPTIONAL
}

ExplicitFormat-ExtIEs F1AP-PROTOCOL-EXTENSION ::= {
   ...
}

ExtendedAvailablePLMN-Item-ExtIEs F1AP-PROTOCOL-EXTENSION ::= {
   ...
}

ExtendedServedPLMNs-List ::= SEQUENCE (SIZE(1.. maxnoofExtendedBPLMNs)) OF ExtendedServedPLMNs-Item

ExtendedServedPLMNs-Item ::= SEQUENCE {
   pLMN-Identity PLMN-Identity,
   tAISliceSupportList SliceSupportList OPTIONAL,
   iE-Extensions ProtocolExtensionContainer { { ExtendedServedPLMNs-ItemExtIEs} } OPTIONAL,
   ...
}

ExtendedServedPLMNs-ItemExtIEs F1AP-PROTOCOL-EXTENSION ::= {
   { ID id-NPNSupportInfo CRITICALITY reject EXTENSION NPNSupportInfo PRESENCE optional }|
   { ID id-ExtendedTAISliceSupportList CRITICALITY reject EXTENSION ExtendedSliceSupportList PRESENCE optional },
   ...
}

ExtendedSliceSupportList ::= SEQUENCE (SIZE(1.. maxnoofExtSliceItems)) OF SliceSupportItem

EUTRACells-List ::= SEQUENCE (SIZE (1.. maxCellineNB)) OF EUTRACells-List-item

EUTRACells-List-item ::= SEQUENCE {
   eUTRA-Cell-ID EUTRA-Cell-ID,
   served-EUTRA-Cells-Information Served-EUTRA-Cells-Information,
   iE-Extensions ProtocolExtensionContainer { { EUTRACells-List-itemExtIEs } } OPTIONAL
}

EUTRACells-List-itemExtIEs F1AP-PROTOCOL-EXTENSION ::= {
   ...
}

EUTRA-Cell-ID ::= BIT STRING (SIZE(28))

EUTRA-Coex-FDD-Info ::= SEQUENCE {
   uL-EARFCN ExtendedEARFCN OPTIONAL,
   dL-EARFCN ExtendedEARFCN,
   uL-Transmission-Bandwidth EUTRA-Transmission-Bandwidth OPTIONAL,
   dL-Transmission-Bandwidth EUTRA-Transmission-Bandwidth,
   iE-Extensions ProtocolExtensionContainer { {EUTRA-Coex-FDD-Info-ExtIEs} } OPTIONAL,
   ...
}

EUTRA-Coex-FDD-Info-ExtIEs F1AP-PROTOCOL-EXTENSION ::= {
   ...
}

EUTRA-Coex-Mode-Info ::= CHOICE {
   fDD EUTRA-Coex-FDD-Info,
   tDD EUTRA-Coex-TDD-Info,
   ...
}

EUTRA-Coex-TDD-Info ::= SEQUENCE {
   eARFCN ExtendedEARFCN,
   transmission-Bandwidth EUTRA-Transmission-Bandwidth,
   subframeAssignment EUTRA-SubframeAssignment,
   specialSubframe-Info EUTRA-SpecialSubframe-Info,
   iE-Extensions ProtocolExtensionContainer { {EUTRA-Coex-TDD-Info-ExtIEs} } OPTIONAL,
   ...
}
EUTRA-Coex-TDD-Info-ExtIEs F1AP-PROTOCOL-EXTENSION ::= {
   ...
}
EUTRA-CyclicPrefixDL ::= ENUMERATED {
   normal,
   extended,
   ...
}

EUTRA-CyclicPrefixUL ::= ENUMERATED {
   normal,
   extended,
   ...
}

EUTRA-PRACH-Configuration ::= SEQUENCE {
   rootSequenceIndex INTEGER (0..837),
   zeroCorrelationIndex INTEGER (0..15),
   highSpeedFlag BOOLEAN,
   prach-FreqOffset INTEGER (0..94),
   prach-ConfigIndex INTEGER (0..63) OPTIONAL,
   -- C-ifTDD: This IE shall be present if the EUTRA-Mode-Info IE in the Resource Coordination E-UTRA Cell Information IE is set to the value "TDD"
   iE-Extensions ProtocolExtensionContainer { {EUTRA-PRACH-Configuration-ExtIEs} } OPTIONAL,
   ...
}

EUTRA-PRACH-Configuration-ExtIEs F1AP-PROTOCOL-EXTENSION ::= {
   ...
}

EUTRA-SpecialSubframe-Info ::= SEQUENCE {
   specialSubframePatterns EUTRA-SpecialSubframePatterns,
   cyclicPrefixDL EUTRA-CyclicPrefixDL,
   cyclicPrefixUL EUTRA-CyclicPrefixUL,
   iE-Extensions ProtocolExtensionContainer { { EUTRA-SpecialSubframe-Info-ExtIEs} } OPTIONAL,
   ...
}

EUTRA-SpecialSubframe-Info-ExtIEs F1AP-PROTOCOL-EXTENSION ::= {
   ...
}

EUTRA-SpecialSubframePatterns ::= ENUMERATED {
   ssp0,
   ssp1,
   ssp2,
   ssp3,
   ssp4,
   ssp5,
   ssp6,
   ssp7,
   ssp8,
   ssp9,
   ssp10,
   ...
}

EUTRA-SubframeAssignment ::= ENUMERATED {
   sa0,
   sa1,
   sa2,
   sa3,
   sa4,
   sa5,
   sa6,
   ...
}

EUTRA-Transmission-Bandwidth ::= ENUMERATED {
   bw6,
   bw15,
   bw25,
   bw50,
   bw75,
   bw100,
   ...
}

EUTRANQoS ::= SEQUENCE {
   qCI QCI,
   allocationAndRetentionPriority AllocationAndRetentionPriority,
   gbrQosInformation GBR-QosInformation OPTIONAL,
   iE-Extensions ProtocolExtensionContainer { { EUTRANQoS-ExtIEs} } OPTIONAL,
   ...
}

EUTRANQoS-ExtIEs F1AP-PROTOCOL-EXTENSION ::= {
   ...
}

ExecuteDuplication ::= ENUMERATED{true,...}

ExtendedEARFCN ::= INTEGER (0..262143)

EUTRA-Mode-Info ::= CHOICE {
   eUTRAFDD EUTRA-FDD-Info,
   eUTRATDD EUTRA-TDD-Info,
   choice-extension ProtocolIE-SingleContainer { { EUTRA-Mode-Info-ExtIEs} }
}

EUTRA-Mode-Info-ExtIEs F1AP-PROTOCOL-IES ::= {
   ...
}

EUTRA-NR-CellResourceCoordinationReq-Container ::= OCTET STRING

EUTRA-NR-CellResourceCoordinationReqAck-Container ::= OCTET STRING

EUTRA-FDD-Info ::= SEQUENCE {
   uL-offsetToPointA OffsetToPointA,
   dL-offsetToPointA OffsetToPointA,
   iE-Extensions ProtocolExtensionContainer { {EUTRA-FDD-Info-ExtIEs} } OPTIONAL,
   ...
}

EUTRA-FDD-Info-ExtIEs F1AP-PROTOCOL-EXTENSION ::= {
   ...
}

EUTRA-TDD-Info ::= SEQUENCE {
   offsetToPointA OffsetToPointA,
   iE-Extensions ProtocolExtensionContainer { {EUTRA-TDD-Info-ExtIEs} } OPTIONAL,
   ...
}

EUTRA-TDD-Info-ExtIEs F1AP-PROTOCOL-EXTENSION ::= {
   ...
}

EventType ::= ENUMERATED {
   on-demand,
   periodic,
   stop,
   ...
}

ExtendedPacketDelayBudget ::= INTEGER (1..65535, ...)

-- F

F1CPathNSA ::= ENUMERATED {lte, nr, both}

F1CTransferPath ::= SEQUENCE {
   f1CPathNSA F1CPathNSA,
   iE-Extensions ProtocolExtensionContainer { { F1CTransferPath-ExtIEs} } OPTIONAL,
   ...
}

F1CTransferPath-ExtIEs F1AP-PROTOCOL-EXTENSION ::= {
   ...
}

FDD-Info ::= SEQUENCE {
   uL-NRFreqInfo NRFreqInfo,
   dL-NRFreqInfo NRFreqInfo,
   uL-Transmission-Bandwidth Transmission-Bandwidth,
   dL-Transmission-Bandwidth Transmission-Bandwidth,
   iE-Extensions ProtocolExtensionContainer { {FDD-Info-ExtIEs} } OPTIONAL,
   ...
}

FDD-Info-ExtIEs F1AP-PROTOCOL-EXTENSION ::= {
   { ID id-ULCarrierList CRITICALITY ignore EXTENSION NRCarrierList PRESENCE optional }|
   { ID id-DLCarrierList CRITICALITY ignore EXTENSION NRCarrierList PRESENCE optional },
   ...
}

Flows-Mapped-To-DRB-List ::= SEQUENCE (SIZE(1.. maxnoofQoSFlows)) OF Flows-Mapped-To-DRB-Item

Flows-Mapped-To-DRB-Item ::= SEQUENCE {
   qoSFlowIdentifier QoSFlowIdentifier,
   qoSFlowLevelQoSParameters QoSFlowLevelQoSParameters,
   iE-Extensions ProtocolExtensionContainer { { Flows-Mapped-To-DRB-ItemExtIEs} } OPTIONAL
}

Flows-Mapped-To-DRB-ItemExtIEs F1AP-PROTOCOL-EXTENSION ::= {
   {ID id-QoSFlowMappingIndication CRITICALITY ignore EXTENSION QoSFlowMappingIndication PRESENCE optional}|
   {ID id-TSCTrafficCharacteristics CRITICALITY ignore EXTENSION TSCTrafficCharacteristics PRESENCE optional},
   ...
}

FR1-Bandwidth ::= ENUMERATED {bw5, bw10, bw20, bw40, bw50, bw80, bw100, ...}

FR2-Bandwidth ::= ENUMERATED {bw50, bw100, bw200, bw400, ...}

FreqBandNrItem ::= SEQUENCE {
   freqBandIndicatorNr INTEGER (1..1024,...),
   supportedSULBandList SEQUENCE (SIZE(0..maxnoofNrCellBands)) OF SupportedSULFreqBandItem,
   iE-Extensions ProtocolExtensionContainer { {FreqBandNrItem-ExtIEs} } OPTIONAL,
   ...
}

FreqBandNrItem-ExtIEs F1AP-PROTOCOL-EXTENSION ::= {
   ...
}

FreqDomainLength ::= CHOICE {
   l839 L839Info,
   l139 L139Info,
   choice-extension ProtocolIE-SingleContainer { {FreqDomainLength-ExtIEs} }
}

FreqDomainLength-ExtIEs F1AP-PROTOCOL-IES ::= {
   ...
}

FrequencyShift7p5khz ::= ENUMERATED {false, true, ...}

FullConfiguration ::= ENUMERATED {full, ...}

FlowsMappedToSLDRB-List ::= SEQUENCE (SIZE(1.. maxnoofPC5QoSFlows)) OF FlowsMappedToSLDRB-Item

FlowsMappedToSLDRB-Item ::= SEQUENCE {
   pc5QoSFlowIdentifier PC5QoSFlowIdentifier,
   iE-Extensions ProtocolExtensionContainer { {FlowsMappedToSLDRB-Item-ExtIEs} } OPTIONAL,
   ...
}

FlowsMappedToSLDRB-Item-ExtIEs F1AP-PROTOCOL-EXTENSION ::= {
   ...
}

-- G

GBR-QosInformation ::= SEQUENCE {
   e-RAB-MaximumBitrateDL BitRate,
   e-RAB-MaximumBitrateUL BitRate,
   e-RAB-GuaranteedBitrateDL BitRate,
   e-RAB-GuaranteedBitrateUL BitRate,
   iE-Extensions ProtocolExtensionContainer { { GBR-QosInformation-ExtIEs} } OPTIONAL,
   ...
}

GBR-QosInformation-ExtIEs F1AP-PROTOCOL-EXTENSION ::= {
   ...
}

GBR-QoSFlowInformation::= SEQUENCE {
   maxFlowBitRateDownlink BitRate,
   maxFlowBitRateUplink BitRate,
   guaranteedFlowBitRateDownlink BitRate,
   guaranteedFlowBitRateUplink BitRate,
   maxPacketLossRateDownlink MaxPacketLossRate OPTIONAL,
   maxPacketLossRateUplink MaxPacketLossRate OPTIONAL,
   iE-Extensions ProtocolExtensionContainer { { GBR-QosFlowInformation-ExtIEs} } OPTIONAL,
   ...
}

GBR-QosFlowInformation-ExtIEs F1AP-PROTOCOL-EXTENSION ::= {
   { ID id-AlternativeQoSParaSetList CRITICALITY ignore EXTENSION AlternativeQoSParaSetList PRESENCE optional },
   ...
}

CG-Config ::= OCTET STRING

GeographicalCoordinates ::= SEQUENCE {
   tRPPositionDefinitionType TRPPositionDefinitionType,
   dLPRSResourceCoordinates DLPRSResourceCoordinates OPTIONAL,
   iE-Extensions ProtocolExtensionContainer { { GeographicalCoordinates-ExtIEs } } OPTIONAL
}

GeographicalCoordinates-ExtIEs F1AP-PROTOCOL-EXTENSION ::= {
   ...
}

GNBCUMeasurementID ::= INTEGER (0.. 4095, ...)

GNBDUMeasurementID ::= INTEGER (0.. 4095, ...)

GNB-CUSystemInformation::= SEQUENCE {
   sibtypetobeupdatedlist SEQUENCE (SIZE(1.. maxnoofSIBTypes)) OF SibtypetobeupdatedListItem,
   iE-Extensions ProtocolExtensionContainer { { GNB-CUSystemInformation-ExtIEs} } OPTIONAL,
   ...
}

GNB-CUSystemInformation-ExtIEs F1AP-PROTOCOL-EXTENSION ::= {
   {ID id-systemInformationAreaID CRITICALITY ignore EXTENSION SystemInformationAreaID PRESENCE optional},
   ...
}

GNB-CU-TNL-Association-Setup-Item::= SEQUENCE {
   tNLAssociationTransportLayerAddress CP-TransportLayerAddress ,
   iE-Extensions ProtocolExtensionContainer { { GNB-CU-TNL-Association-Setup-Item-ExtIEs} } OPTIONAL
}

GNB-CU-TNL-Association-Setup-Item-ExtIEs F1AP-PROTOCOL-EXTENSION ::= {
   ...
}

GNB-CU-TNL-Association-Failed-To-Setup-Item ::= SEQUENCE {
   tNLAssociationTransportLayerAddress CP-TransportLayerAddress ,
   cause Cause,
   iE-Extensions ProtocolExtensionContainer { { GNB-CU-TNL-Association-Failed-To-Setup-Item-ExtIEs} } OPTIONAL
}

GNB-CU-TNL-Association-Failed-To-Setup-Item-ExtIEs F1AP-PROTOCOL-EXTENSION ::= {
   ...
}

GNB-CU-TNL-Association-To-Add-Item ::= SEQUENCE {
   tNLAssociationTransportLayerAddress CP-TransportLayerAddress ,
   tNLAssociationUsage TNLAssociationUsage,
   iE-Extensions ProtocolExtensionContainer { { GNB-CU-TNL-Association-To-Add-Item-ExtIEs} } OPTIONAL
}

GNB-CU-TNL-Association-To-Add-Item-ExtIEs F1AP-PROTOCOL-EXTENSION ::= {
   ...
}

GNB-CU-TNL-Association-To-Remove-Item::= SEQUENCE {
   tNLAssociationTransportLayerAddress CP-TransportLayerAddress ,
   iE-Extensions ProtocolExtensionContainer { { GNB-CU-TNL-Association-To-Remove-Item-ExtIEs} } OPTIONAL
}

GNB-CU-TNL-Association-To-Remove-Item-ExtIEs F1AP-PROTOCOL-EXTENSION ::= {
   {ID id-TNLAssociationTransportLayerAddressgNBDU CRITICALITY reject EXTENSION CP-TransportLayerAddress PRESENCE optional},
   ...
}

GNB-CU-TNL-Association-To-Update-Item::= SEQUENCE {
   tNLAssociationTransportLayerAddress CP-TransportLayerAddress ,
   tNLAssociationUsage TNLAssociationUsage OPTIONAL,
   iE-Extensions ProtocolExtensionContainer { { GNB-CU-TNL-Association-To-Update-Item-ExtIEs} } OPTIONAL
}

GNB-CU-TNL-Association-To-Update-Item-ExtIEs F1AP-PROTOCOL-EXTENSION ::= {
   ...
}

GNB-CU-UE-F1AP-ID ::= INTEGER (0..4294967295)

GNB-DU-Cell-Resource-Configuration ::= SEQUENCE {
   subcarrierSpacing SubcarrierSpacing,
   dUFTransmissionPeriodicity DUFTransmissionPeriodicity OPTIONAL,
   dUF-Slot-Config-List DUF-Slot-Config-List OPTIONAL,
   hSNATransmissionPeriodicity HSNATransmissionPeriodicity,
   hNSASlotConfigList HSNASlotConfigList OPTIONAL,
   iE-Extensions ProtocolExtensionContainer { { GNB-DU-Cell-Resource-Configuration-ExtIEs } } OPTIONAL
}

GNB-DU-Cell-Resource-Configuration-ExtIEs F1AP-PROTOCOL-EXTENSION ::= {
   ...
}

GNB-DU-UE-F1AP-ID ::= INTEGER (0..4294967295)

GNB-DU-ID ::= INTEGER (0..68719476735)

GNB-CU-Name ::= PrintableString(SIZE(1..150,...))

GNB-DU-Name ::= PrintableString(SIZE(1..150,...))

Extended-GNB-CU-Name ::= SEQUENCE {
   gNB-CU-NameVisibleString GNB-CU-NameVisibleString OPTIONAL,
   gNB-CU-NameUTF8String GNB-CU-NameUTF8String OPTIONAL,
   iE-Extensions ProtocolExtensionContainer { { Extended-GNB-CU-Name-ExtIEs } } OPTIONAL,
   ...
}

Extended-GNB-CU-Name-ExtIEs F1AP-PROTOCOL-EXTENSION ::= {
   ...
}

GNB-CU-NameVisibleString ::= VisibleString(SIZE(1..150,...))

GNB-CU-NameUTF8String ::= UTF8String(SIZE(1..150,...))

Extended-GNB-DU-Name ::= SEQUENCE {
   gNB-DU-NameVisibleString GNB-DU-NameVisibleString OPTIONAL,
   gNB-DU-NameUTF8String GNB-DU-NameUTF8String OPTIONAL,
   iE-Extensions ProtocolExtensionContainer { { Extended-GNB-DU-Name-ExtIEs } } OPTIONAL,
   ...
}

Extended-GNB-DU-Name-ExtIEs F1AP-PROTOCOL-EXTENSION ::= {
   ...
}

GNB-DU-NameVisibleString ::= VisibleString(SIZE(1..150,...))

GNB-DU-NameUTF8String ::= UTF8String(SIZE(1..150,...))

GNB-DU-Served-Cells-Item ::= SEQUENCE {
   served-Cell-Information Served-Cell-Information,
   gNB-DU-System-Information GNB-DU-System-Information OPTIONAL,
   iE-Extensions ProtocolExtensionContainer { { GNB-DU-Served-Cells-ItemExtIEs} } OPTIONAL,
   ...
}

GNB-DU-Served-Cells-ItemExtIEs F1AP-PROTOCOL-EXTENSION ::= {
   ...
}

GNB-DU-System-Information ::= SEQUENCE {
   mIB-message MIB-message,
   sIB1-message SIB1-message,
   iE-Extensions ProtocolExtensionContainer { { GNB-DU-System-Information-ExtIEs } } OPTIONAL,
   ...
}

GNB-DU-System-Information-ExtIEs F1AP-PROTOCOL-EXTENSION ::= {
   { ID id-SIB12-message CRITICALITY ignore EXTENSION SIB12-message PRESENCE optional}|
   { ID id-SIB13-message CRITICALITY ignore EXTENSION SIB13-message PRESENCE optional}|
   { ID id-SIB14-message CRITICALITY ignore EXTENSION SIB14-message PRESENCE optional}|
   { ID id-SIB10-message CRITICALITY ignore EXTENSION SIB10-message PRESENCE optional},
   ...
}

GNB-DUConfigurationQuery ::= ENUMERATED {true, ...}

GNBDUOverloadInformation ::= ENUMERATED {overloaded, not-overloaded}

GNB-DU-TNL-Association-To-Remove-Item::= SEQUENCE {
   tNLAssociationTransportLayerAddress CP-TransportLayerAddress ,
   tNLAssociationTransportLayerAddressgNBCU CP-TransportLayerAddress OPTIONAL,
   iE-Extensions ProtocolExtensionContainer { { GNB-DU-TNL-Association-To-Remove-Item-ExtIEs} } OPTIONAL
}

GNB-DU-TNL-Association-To-Remove-Item-ExtIEs F1AP-PROTOCOL-EXTENSION ::= {
   ...
}

GNB-RxTxTimeDiff ::= SEQUENCE {
   rxTxTimeDiff GNBRxTxTimeDiffMeas,
   additionalPath-List AdditionalPath-List OPTIONAL,
   iE-Extensions ProtocolExtensionContainer { { GNB-RxTxTimeDiff-ExtIEs} } OPTIONAL
}

GNB-RxTxTimeDiff-ExtIEs F1AP-PROTOCOL-EXTENSION ::= {

   ...
}

GNBRxTxTimeDiffMeas ::= CHOICE {
   k0 INTEGER (0.. 1970049),
   k1 INTEGER (0.. 985025),
   k2 INTEGER (0.. 492513),
   k3 INTEGER (0.. 246257),
   k4 INTEGER (0.. 123129),
   k5 INTEGER (0.. 61565),
   choice-extension ProtocolIE-SingleContainer { { GNBRxTxTimeDiffMeas-ExtIEs } }
}

GNBRxTxTimeDiffMeas-ExtIEs F1AP-PROTOCOL-IES ::= {
   ...
}

GNBSetID ::= BIT STRING (SIZE(22))

GTP-TEID ::= OCTET STRING (SIZE (4))

GTPTLAs ::= SEQUENCE (SIZE(1.. maxnoofGTPTLAs)) OF GTPTLA-Item

GTPTLA-Item ::= SEQUENCE {
   gTPTransportLayerAddress TransportLayerAddress,
   iE-Extensions ProtocolExtensionContainer { { GTPTLA-Item-ExtIEs } } OPTIONAL
}

GTPTLA-Item-ExtIEs F1AP-PROTOCOL-EXTENSION ::= {
   ...
}

GTPTunnel ::= SEQUENCE {
   transportLayerAddress TransportLayerAddress,
   gTP-TEID GTP-TEID,
   iE-Extensions ProtocolExtensionContainer { { GTPTunnel-ExtIEs } } OPTIONAL,
   ...
}

GTPTunnel-ExtIEs F1AP-PROTOCOL-EXTENSION ::= {
   ...
}

-- H

HandoverPreparationInformation ::= OCTET STRING

HardwareLoadIndicator ::= SEQUENCE {
   dLHardwareLoadIndicator INTEGER (0..100, ...),
   uLHardwareLoadIndicator INTEGER (0..100, ...),
   iE-Extensions ProtocolExtensionContainer { { HardwareLoadIndicator-ExtIEs } } OPTIONAL,
   ...
}

HardwareLoadIndicator-ExtIEs F1AP-PROTOCOL-EXTENSION ::= {
   ...
}

HSNASlotConfigList ::= SEQUENCE (SIZE(1..maxnoofHSNASlots)) OF HSNASlotConfigItem

HSNASlotConfigItem ::= SEQUENCE {
   hSNADownlink HSNADownlink OPTIONAL,
   hSNAUplink HSNAUplink OPTIONAL,
   hSNAFlexible HSNAFlexible OPTIONAL,
   iE-Extensions ProtocolExtensionContainer { { HSNASlotConfigItem-ExtIEs } } OPTIONAL
}

HSNASlotConfigItem-ExtIEs F1AP-PROTOCOL-EXTENSION ::= {
   ...
}
HSNADownlink ::= ENUMERATED { hard, soft, notavailable }

HSNAFlexible ::= ENUMERATED { hard, soft, notavailable }

HSNAUplink ::= ENUMERATED { hard, soft, notavailable }

HSNATransmissionPeriodicity ::= ENUMERATED { ms0p5, ms0p625, ms1, ms1p25, ms2, ms2p5, ms5, ms10, ms20, ms40, ms80, ms160, ...}

-- I

IAB-Barred ::= ENUMERATED {barred, not-barred, ...}

IAB-Info-IAB-donor-CU ::= SEQUENCE{
   iAB-STC-Info IAB-STC-Info OPTIONAL,
   iE-Extensions ProtocolExtensionContainer { { IAB-Info-IAB-donor-CU-ExtIEs } } OPTIONAL
}

IAB-Info-IAB-donor-CU-ExtIEs F1AP-PROTOCOL-EXTENSION ::= {
   ...
}

IAB-Info-IAB-DU ::= SEQUENCE{
   multiplexingInfo MultiplexingInfo OPTIONAL,
   iAB-STC-Info IAB-STC-Info OPTIONAL,
   iE-Extensions ProtocolExtensionContainer { { IAB-Info-IAB-DU-ExtIEs } } OPTIONAL
}

IAB-Info-IAB-DU-ExtIEs F1AP-PROTOCOL-EXTENSION ::= {
   ...
}

IAB-MT-Cell-List ::= SEQUENCE (SIZE(1..maxnoofServingCells)) OF IAB-MT-Cell-List-Item

IAB-MT-Cell-List-Item ::= SEQUENCE {
   nRCellIdentity NRCellIdentity,
   dU-RX-MT-RX DU-RX-MT-RX,
   dU-TX-MT-TX DU-TX-MT-TX,
   dU-RX-MT-TX DU-RX-MT-TX,
   dU-TX-MT-RX DU-TX-MT-RX,
   iE-Extensions ProtocolExtensionContainer { { IAB-MT-Cell-List-Item-ExtIEs } } OPTIONAL
}

IAB-MT-Cell-List-Item-ExtIEs F1AP-PROTOCOL-EXTENSION ::= {
   ...
}

IAB-STC-Info ::= SEQUENCE{
   iAB-STC-Info-List IAB-STC-Info-List,
   iE-Extensions ProtocolExtensionContainer { { IAB-STC-Info-ExtIEs } } OPTIONAL
}

IAB-STC-Info-ExtIEs F1AP-PROTOCOL-EXTENSION ::= {
   ...
}

IAB-STC-Info-List ::= SEQUENCE (SIZE(1..maxnoofIABSTCInfo)) OF IAB-STC-Info-Item

IAB-STC-Info-Item::= SEQUENCE {
   sSB-freqInfo SSB-freqInfo,
   sSB-subcarrierSpacing SSB-subcarrierSpacing,
   sSB-transmissionPeriodicity SSB-transmissionPeriodicity,
   sSB-transmissionTimingOffset SSB-transmissionTimingOffset,
   sSB-transmissionBitmap SSB-transmissionBitmap,
   iE-Extensions ProtocolExtensionContainer { { IAB-STC-Info-Item-ExtIEs } } OPTIONAL
}

IAB-STC-Info-Item-ExtIEs F1AP-PROTOCOL-EXTENSION ::= {
   ...
}

IAB-Allocated-TNL-Address-Item ::= SEQUENCE {
   iABTNLAddress IABTNLAddress,
   iABTNLAddressUsage IABTNLAddressUsage OPTIONAL,
   iE-Extensions ProtocolExtensionContainer { { IAB-Allocated-TNL-Address-Item-ExtIEs } } OPTIONAL
}

IAB-Allocated-TNL-Address-Item-ExtIEs F1AP-PROTOCOL-EXTENSION ::= {
   ...
}

IAB-DU-Cell-Resource-Configuration-Mode-Info ::= CHOICE {
   fDD IAB-DU-Cell-Resource-Configuration-FDD-Info,
   tDD IAB-DU-Cell-Resource-Configuration-TDD-Info,
   choice-extension ProtocolIE-SingleContainer { { IAB-DU-Cell-Resource-Configuration-Mode-Info-ExtIEs} }
}

IAB-DU-Cell-Resource-Configuration-Mode-Info-ExtIEs F1AP-PROTOCOL-IES ::= {
   ...
}

IAB-DU-Cell-Resource-Configuration-FDD-Info ::= SEQUENCE {
   gNB-DU-Cell-Resource-Configuration-FDD-UL GNB-DU-Cell-Resource-Configuration,
   gNB-DU-Cell-Resource-Configuration-FDD-DL GNB-DU-Cell-Resource-Configuration,
   iE-Extensions ProtocolExtensionContainer { {IAB-DU-Cell-Resource-Configuration-FDD-Info-ExtIEs} } OPTIONAL,
   ...
}

IAB-DU-Cell-Resource-Configuration-FDD-Info-ExtIEs F1AP-PROTOCOL-EXTENSION ::= {
   ...
}

IAB-DU-Cell-Resource-Configuration-TDD-Info ::= SEQUENCE {
   gNB-DU-Cell-Resourc-Configuration-TDD GNB-DU-Cell-Resource-Configuration,
   iE-Extensions ProtocolExtensionContainer { {IAB-DU-Cell-Resource-Configuration-TDD-Info-ExtIEs} } OPTIONAL,
   ...
}

IAB-DU-Cell-Resource-Configuration-TDD-Info-ExtIEs F1AP-PROTOCOL-EXTENSION ::= {
   ...
}

IABIPv6RequestType ::= CHOICE {
   iPv6Address IABTNLAddressesRequested,
   iPv6Prefix IABTNLAddressesRequested,
   choice-extension ProtocolIE-SingleContainer { { IABIPv6RequestType-ExtIEs} }
}

IABIPv6RequestType-ExtIEs F1AP-PROTOCOL-IES ::= {
   ...
}

IABTNLAddress ::= CHOICE {
   iPv4Address BIT STRING (SIZE(32)),
   iPv6Address BIT STRING (SIZE(128)),
   iPv6Prefix BIT STRING (SIZE(64)),
   choice-extension ProtocolIE-SingleContainer { { IABTNLAddress-ExtIEs} }
}

IABTNLAddress-ExtIEs F1AP-PROTOCOL-IES ::= {
   ...
}

IABTNLAddressesRequested ::= SEQUENCE {
   tNLAddressesOrPrefixesRequestedAllTraffic INTEGER (1..256) OPTIONAL,
   tNLAddressesOrPrefixesRequestedF1-C INTEGER (1..256) OPTIONAL,
   tNLAddressesOrPrefixesRequestedF1-U INTEGER (1..256) OPTIONAL,
   tNLAddressesOrPrefixesRequestedNoNF1 INTEGER (1..256) OPTIONAL,
   iE-Extensions ProtocolExtensionContainer { { IABTNLAddressesRequested-ExtIEs } } OPTIONAL
}

IABTNLAddressesRequested-ExtIEs F1AP-PROTOCOL-EXTENSION ::= {
   ...
}

IAB-TNL-Addresses-To-Remove-Item ::= SEQUENCE {
   iABTNLAddress IABTNLAddress,
   iE-Extensions ProtocolExtensionContainer { { IAB-TNL-Addresses-To-Remove-Item-ExtIEs} } OPTIONAL
}

IAB-TNL-Addresses-To-Remove-Item-ExtIEs F1AP-PROTOCOL-EXTENSION ::= {
   ...
}

IABTNLAddressUsage ::= ENUMERATED {
   f1-c,
   f1-u,
   non-f1,
   ...
}

IABv4AddressesRequested ::= SEQUENCE {
   iABv4AddressesRequested IABTNLAddressesRequested,
   iE-Extensions ProtocolExtensionContainer { { IABv4AddressesRequested-ExtIEs} } OPTIONAL
}

IABv4AddressesRequested-ExtIEs F1AP-PROTOCOL-EXTENSION ::= {
   ...
}

ImplicitFormat ::= SEQUENCE {
   dUFSlotformatIndex DUFSlotformatIndex,
   iE-Extensions ProtocolExtensionContainer { { ImplicitFormat-ExtIEs } } OPTIONAL
}

ImplicitFormat-ExtIEs F1AP-PROTOCOL-EXTENSION ::= {
   ...
}

IgnorePRACHConfiguration::= ENUMERATED { true,...}

IgnoreResourceCoordinationContainer ::= ENUMERATED { yes,...}
InactivityMonitoringRequest ::= ENUMERATED { true,...}
InactivityMonitoringResponse ::= ENUMERATED { not-supported,...}
InterfacesToTrace ::= BIT STRING (SIZE(8))

IntendedTDD-DL-ULConfig ::= SEQUENCE {
   nRSCS ENUMERATED { scs15, scs30, scs60, scs120,...},
   nRCP ENUMERATED { normal, extended,...},
   nRDLULTxPeriodicity ENUMERATED { ms0p5, ms0p625, ms1,
     ms1p25, ms2, ms2p5, ms3, ms4, ms5, ms10, ms20,
     ms40, ms60, ms80, ms100, ms120, ms140, ms160, ...},
   slot-Configuration-List Slot-Configuration-List,
   iE-Extensions ProtocolExtensionContainer { {IntendedTDD-DL-ULConfig-ExtIEs} } OPTIONAL
}

IntendedTDD-DL-ULConfig-ExtIEs F1AP-PROTOCOL-EXTENSION ::= {
   ...
}

IPHeaderInformation ::= SEQUENCE {
   destinationIABTNLAddress IABTNLAddress,
   dsInformationList DSInformationList OPTIONAL,
   iPv6FlowLabel BIT STRING (SIZE (20)) OPTIONAL,
   iE-Extensions ProtocolExtensionContainer { { IPHeaderInformation-ItemExtIEs} } OPTIONAL,
   ...
}

IPHeaderInformation-ItemExtIEs F1AP-PROTOCOL-EXTENSION ::= {
   ...
}

IPtolayer2TrafficMappingInfo ::= SEQUENCE {
   iPtolayer2TrafficMappingInfoToAdd IPtolayer2TrafficMappingInfoList OPTIONAL,
   iPtolayer2TrafficMappingInfoToRemove MappingInformationtoRemove OPTIONAL,
   iE-Extensions ProtocolExtensionContainer { { IPtolayer2TrafficMappingInfo-ItemExtIEs} } OPTIONAL,
   ...
}

IPtolayer2TrafficMappingInfoList ::= SEQUENCE (SIZE(1..maxnoofMappingEntries)) OF IPtolayer2TrafficMappingInfo-Item

IPtolayer2TrafficMappingInfo-Item ::= SEQUENCE {
   mappingInformationIndex MappingInformationIndex,
   iPHeaderInformation IPHeaderInformation,
   bHInfo BHInfo, iE-Extensions ProtocolExtensionContainer { { IPtolayer2TrafficMappingInfo-ItemExtIEs} } OPTIONAL,
   ...
}

IPtolayer2TrafficMappingInfo-ItemExtIEs F1AP-PROTOCOL-EXTENSION ::= {
   ...
}

-- J

-- K

-- L

L139Info ::= SEQUENCE {
   msg1SCS ENUMERATED {scs15, scs30, scs60, scs120, ...},
   rootSequenceIndex INTEGER (0..137) OPTIONAL,
   iE-Extension ProtocolExtensionContainer { {L139Info-ExtIEs} } OPTIONAL,
   ...
}

L139Info-ExtIEs F1AP-PROTOCOL-EXTENSION ::= {
   ...
}

L839Info ::= SEQUENCE {
   rootSequenceIndex INTEGER (0..837),
   restrictedSetConfig ENUMERATED {unrestrictedSet, restrictedSetTypeA,
      restrictedSetTypeB, ...},
   iE-Extension ProtocolExtensionContainer { {L839Info-ExtIEs} } OPTIONAL,
   ...
}

L839Info-ExtIEs F1AP-PROTOCOL-EXTENSION ::= {
   ...
}

LCID ::= INTEGER (1..32, ...)

LCS-to-GCS-TranslationAoA::= SEQUENCE {
   alpha INTEGER (0..3599),
   beta INTEGER (0..3599),
   gamma INTEGER (0..3599),
   iE-Extensions ProtocolExtensionContainer { { LCS-to-GCS-TranslationAoA-ExtIEs} } OPTIONAL,
   ...
}

LCS-to-GCS-TranslationAoA-ExtIEs F1AP-PROTOCOL-EXTENSION ::= {
   ...
}

LCStoGCSTranslationList ::= SEQUENCE (SIZE (1.. maxnooflcs-gcs-translation)) OF LCStoGCSTranslation

LCStoGCSTranslation ::= SEQUENCE {
   alpha INTEGER (0..359),
   alpha-fine INTEGER (0..9) OPTIONAL,
   beta INTEGER (0..359),
   beta-fine INTEGER (0..9) OPTIONAL,
   gamma INTEGER (0..359),
   gamma-fine INTEGER (0..9) OPTIONAL,
   iE-Extensions ProtocolExtensionContainer { {LCStoGCSTranslation-ExtIEs} } OPTIONAL
}

LCStoGCSTranslation-ExtIEs F1AP-PROTOCOL-EXTENSION ::= {
   ...
}

LMF-MeasurementID ::= INTEGER (1.. 65536, ...)

LMF-UE-MeasurementID ::= INTEGER (1.. 256, ...)

LocationUncertainty ::= SEQUENCE {
   horizontalUncertainty INTEGER (0..255),
   horizontalConfidence INTEGER (0..100),
   verticalUncertainty INTEGER (0..255),
   verticalConfidence INTEGER (0..100),
   iE-Extensions ProtocolExtensionContainer { { LocationUncertainty-ExtIEs} } OPTIONAL
}

LocationUncertainty-ExtIEs F1AP-PROTOCOL-EXTENSION ::= {
   ...
}

LongDRXCycleLength ::= ENUMERATED
{ms10, ms20, ms32, ms40, ms60, ms64, ms70, ms80,
  ms128, ms160, ms256, ms320, ms512, ms640,
  ms1024, ms1280, ms2048, ms2560, ms5120, ms10240, ...}

LowerLayerPresenceStatusChange ::= ENUMERATED {
   suspend-lower-layers,
   resume-lower-layers,
   ...

}

LTEUESidelinkAggregateMaximumBitrate ::= SEQUENCE {
   uELTESidelinkAggregateMaximumBitrate BitRate,
   iE-Extensions ProtocolExtensionContainer { {LTEUESidelinkAggregateMaximumBitrate-ExtIEs} } OPTIONAL
}

LTEUESidelinkAggregateMaximumBitrate-ExtIEs F1AP-PROTOCOL-EXTENSION ::= {
   ...
}

LTEV2XServicesAuthorized ::= SEQUENCE {
   vehicleUE VehicleUE OPTIONAL,
   pedestrianUE PedestrianUE OPTIONAL,
   iE-Extensions ProtocolExtensionContainer { {LTEV2XServicesAuthorized-ExtIEs} } OPTIONAL
}

LTEV2XServicesAuthorized-ExtIEs F1AP-PROTOCOL-EXTENSION ::= {
   ...
}

-- M

MappingInformationIndex ::= BIT STRING (SIZE (26))

MappingInformationtoRemove ::= SEQUENCE (SIZE(1..maxnoofMappingEntries)) OF MappingInformationIndex

MaskedIMEISV ::= BIT STRING (SIZE (64))

MaxDataBurstVolume ::= INTEGER (0..4095, ..., 4096.. 2000000)
MaxPacketLossRate ::= INTEGER (0..1000)

MIB-message ::= OCTET STRING

MeasConfig ::= OCTET STRING

MeasGapConfig ::= OCTET STRING

MeasGapSharingConfig ::= OCTET STRING

MeasurementBeamInfoRequest ::= ENUMERATED {true, ...}

MeasurementBeamInfo ::= SEQUENCE {
   pRS-Resource-ID PRS-Resource-ID OPTIONAL,
   pRS-Resource-Set-ID PRS-Resource-Set-ID OPTIONAL,
   sSB-Index SSB-Index OPTIONAL,
   iE-Extensions ProtocolExtensionContainer { { MeasurementBeamInfo-ExtIEs} } OPTIONAL
}

MeasurementBeamInfo-ExtIEs F1AP-PROTOCOL-EXTENSION ::= {
   ...
}

MeasurementTimingConfiguration ::= OCTET STRING

MessageIdentifier ::= BIT STRING (SIZE (16))

MultiplexingInfo ::= SEQUENCE{
   iAB-MT-Cell-List IAB-MT-Cell-List,
   iE-Extensions ProtocolExtensionContainer { {MultiplexingInfo-ExtIEs} } OPTIONAL
}

MultiplexingInfo-ExtIEs F1AP-PROTOCOL-EXTENSION ::= {
   ...
}

M2Configuration ::= ENUMERATED {true, ...}

M5Configuration ::= SEQUENCE {
   m5period M5period,
   m5-links-to-log M5-Links-to-log,
   iE-Extensions ProtocolExtensionContainer { { M5Configuration-ExtIEs} } OPTIONAL,
   ...
}

M5Configuration-ExtIEs F1AP-PROTOCOL-EXTENSION ::= {
   ...
}

M5period ::= ENUMERATED { ms1024, ms2048, ms5120, ms10240, min1, ... }

M5-Links-to-log ::= ENUMERATED {uplink, downlink, both-uplink-and-downlink, ...}

M6Configuration ::= SEQUENCE {
   m6report-Interval M6report-Interval,
   m6-links-to-log M6-Links-to-log,
   iE-Extensions ProtocolExtensionContainer { { M6Configuration-ExtIEs} } OPTIONAL,
   ...
}

M6Configuration-ExtIEs F1AP-PROTOCOL-EXTENSION ::= {
   ...
}

M6report-Interval ::= ENUMERATED { ms120, ms240, ms640, ms1024, ms2048, ms5120, ms10240, ms20480, ms40960, min1, min6, min12, min30, ... }

M6-Links-to-log ::= ENUMERATED {uplink, downlink, both-uplink-and-downlink, ...}

M7Configuration ::= SEQUENCE {
   m7period M7period,
   m7-links-to-log M7-Links-to-log,
   iE-Extensions ProtocolExtensionContainer { { M7Configuration-ExtIEs} } OPTIONAL,
   ...
}

M7Configuration-ExtIEs F1AP-PROTOCOL-EXTENSION ::= {
   ...
}

M7period ::= INTEGER(1..60, ...)

M7-Links-to-log ::= ENUMERATED {downlink, ...}

MDT-Activation ::= ENUMERATED {
   immediate-MDT-only,
   immediate-MDT-and-Trace,
   ...
}

MDTConfiguration ::= SEQUENCE {
   mdt-Activation MDT-Activation,
   measurementsToActivate MeasurementsToActivate,
   m2Configuration M2Configuration OPTIONAL,
   -- C-ifM2: This IE shall be present if the Measurements to Activate IE has the second bit set to "1".
   m5Configuration M5Configuration OPTIONAL,
   -- C-ifM5: This IE shall be present if the Measurements to Activate IE has the fifth bit set to "1".
   m6Configuration M6Configuration OPTIONAL,
   -- C-ifM6: This IE shall be present if the Measurements to Activate IE has the seventh bit set to "1".
   m7Configuration M7Configuration OPTIONAL,
   -- C-ifM7: This IE shall be present if the Measurements to Activate IE has the eighth bit set to "1".
   iE-Extensions ProtocolExtensionContainer { { MDTConfiguration-ExtIEs} } OPTIONAL,
   ...
}
MDTConfiguration-ExtIEs F1AP-PROTOCOL-EXTENSION ::= {
   ...
}

MDTPLMNList ::= SEQUENCE (SIZE(1..maxnoofMDTPLMNs)) OF PLMN-Identity

MeasuredResultsValue ::= CHOICE {
   uL-AngleOfArrival UL-AoA,
   uL-SRS-RSRP UL-SRS-RSRP,
   uL-RTOA UL-RTOA-Measurement,
   gNB-RxTxTimeDiff GNB-RxTxTimeDiff,
   choice-extension ProtocolIE-SingleContainer { { MeasuredResultsValue-ExtIEs } }
}

MeasuredResultsValue-ExtIEs F1AP-PROTOCOL-IES ::= {
   ...
}

MeasurementsToActivate ::= BIT STRING (SIZE (8))

-- N

NeedforGap::= ENUMERATED {true, ...}

Neighbour-Cell-Information-Item ::= SEQUENCE {
   nRCGI NRCGI,
   intendedTDD-DL-ULConfig IntendedTDD-DL-ULConfig OPTIONAL,
   iE-Extensions ProtocolExtensionContainer { { Neighbour-Cell-Information-ItemExtIEs } } OPTIONAL
}

Neighbour-Cell-Information-ItemExtIEs F1AP-PROTOCOL-EXTENSION ::= {
   ...
}

NGRANAllocationAndRetentionPriority ::= SEQUENCE {
   priorityLevel PriorityLevel,
   pre-emptionCapability Pre-emptionCapability,
   pre-emptionVulnerability Pre-emptionVulnerability,
   iE-Extensions ProtocolExtensionContainer { {NGRANAllocationAndRetentionPriority-ExtIEs} } OPTIONAL
}

NGRANAllocationAndRetentionPriority-ExtIEs F1AP-PROTOCOL-EXTENSION ::= {
   ...
}

NGRANHighAccuracyAccessPointPosition ::= SEQUENCE {
   latitude INTEGER (-2147483648.. 2147483647),
   longitude INTEGER (-2147483648.. 2147483647),
   altitude INTEGER (-64000..1280000),
   uncertaintySemi-major INTEGER (0..255),
   uncertaintySemi-minor INTEGER (0..255),
   orientationOfMajorAxis INTEGER (0..179),
   horizontalConfidence INTEGER (0..100),
   uncertaintyAltitude INTEGER (0..255),
   verticalConfidence INTEGER (0..100),

   iE-Extensions ProtocolExtensionContainer { { NGRANHighAccuracyAccessPointPosition-ExtIEs} } OPTIONAL
}

NGRANHighAccuracyAccessPointPosition-ExtIEs F1AP-PROTOCOL-EXTENSION ::= {
   ...
}

NID ::= BIT STRING (SIZE(44))

NR-CGI-List-For-Restart-Item ::= SEQUENCE {
   nRCGI NRCGI,
   iE-Extensions ProtocolExtensionContainer { { NR-CGI-List-For-Restart-ItemExtIEs } } OPTIONAL,
   ...
}

NR-CGI-List-For-Restart-ItemExtIEs F1AP-PROTOCOL-EXTENSION ::= {
   ...
}

NR-PRSBeamInformation ::= SEQUENCE {
   nR-PRSBeamInformationList NR-PRSBeamInformationList,
   lCStoGCSTranslationList LCStoGCSTranslationList OPTIONAL,
   iE-Extensions ProtocolExtensionContainer { { NR-PRSBeamInformation-ExtIEs } } OPTIONAL
}

NR-PRSBeamInformation-ExtIEs F1AP-PROTOCOL-EXTENSION ::= {
   ...
}

NR-PRSBeamInformationList ::= SEQUENCE (SIZE(1.. maxnoofPRS-ResourceSets)) OF NR-PRSBeamInformationItem

NR-PRSBeamInformationItem ::= SEQUENCE {
   pRSResourceSetID PRS-Resource-Set-ID,
   pRSAngleList PRSAngleList,
   iE-Extensions ProtocolExtensionContainer { { NR-PRSBeamInformationItem-ExtIEs } } OPTIONAL
}

NR-PRSBeamInformationItem-ExtIEs F1AP-PROTOCOL-EXTENSION ::= {
   ...
}

NonDynamic5QIDescriptor ::= SEQUENCE {
   fiveQI INTEGER (0..255, ...),
   qoSPriorityLevel INTEGER (1..127) OPTIONAL,
   averagingWindow AveragingWindow OPTIONAL,
   maxDataBurstVolume MaxDataBurstVolume OPTIONAL,
   iE-Extensions ProtocolExtensionContainer { { NonDynamic5QIDescriptor-ExtIEs } } OPTIONAL
}

NonDynamic5QIDescriptor-ExtIEs F1AP-PROTOCOL-EXTENSION ::= {
   { ID id-CNPacketDelayBudgetDownlink CRITICALITY ignore EXTENSION ExtendedPacketDelayBudget PRESENCE optional }|
   { ID id-CNPacketDelayBudgetUplink CRITICALITY ignore EXTENSION ExtendedPacketDelayBudget PRESENCE optional },
   ...
}

NonDynamicPQIDescriptor ::= SEQUENCE {
   fiveQI INTEGER (0..255, ...),
   qoSPriorityLevel INTEGER (1..8, ...) OPTIONAL,
   averagingWindow AveragingWindow OPTIONAL,
   maxDataBurstVolume MaxDataBurstVolume OPTIONAL,
   iE-Extensions ProtocolExtensionContainer { { NonDynamicPQIDescriptor-ExtIEs } } OPTIONAL
}

NonDynamicPQIDescriptor-ExtIEs F1AP-PROTOCOL-EXTENSION ::= {
   ...
}

NonUPTrafficType ::= ENUMERATED {ue-associated, non-ue-associated, non-f1, bap-control-pdu,...}

NoofDownlinkSymbols ::= INTEGER (0..14)

NoofUplinkSymbols ::= INTEGER (0..14)

Notification-Cause ::= ENUMERATED {fulfilled, not-fulfilled, ...}

NotificationControl ::= ENUMERATED {active, not-active, ...}

NotificationInformation ::= SEQUENCE {
   message-Identifier MessageIdentifier,
   serialNumber SerialNumber,
   iE-Extensions ProtocolExtensionContainer { { NotificationInformationExtIEs} } OPTIONAL,
   ...
}

NotificationInformationExtIEs F1AP-PROTOCOL-EXTENSION ::= {
   ...
}

NPNBroadcastInformation ::= CHOICE {
   sNPN-Broadcast-Information NPN-Broadcast-Information-SNPN,
   pNI-NPN-Broadcast-Information NPN-Broadcast-Information-PNI-NPN,
   choice-extension ProtocolIE-SingleContainer { {NPNBroadcastInformation-ExtIEs} }
}

NPNBroadcastInformation-ExtIEs F1AP-PROTOCOL-IES ::= {
   ...
}

NPN-Broadcast-Information-SNPN ::= SEQUENCE {
   broadcastSNPNID-List BroadcastSNPN-ID-List,
   iE-Extension ProtocolExtensionContainer { {NPN-Broadcast-Information-SNPN-ExtIEs} } OPTIONAL,
   ...
}

NPN-Broadcast-Information-SNPN-ExtIEs F1AP-PROTOCOL-EXTENSION ::= {
   ...
}
NPN-Broadcast-Information-PNI-NPN ::= SEQUENCE {
   broadcastPNI-NPN-ID-Information BroadcastPNI-NPN-ID-List,
   iE-Extension ProtocolExtensionContainer { {NPN-Broadcast-Information-PNI-NPN-ExtIEs} } OPTIONAL,
   ...
}

NPN-Broadcast-Information-PNI-NPN-ExtIEs F1AP-PROTOCOL-EXTENSION ::= {
   ...
}

NPNSupportInfo ::= CHOICE {
   sNPN-Information NID,
   choice-extension ProtocolIE-SingleContainer { { NPNSupportInfo-ExtIEs } }
}

NPNSupportInfo-ExtIEs F1AP-PROTOCOL-IES ::= {
   ...
}

NRCarrierList ::= SEQUENCE (SIZE(1..maxnoofNRSCSs)) OF NRCarrierItem

NRCarrierItem ::= SEQUENCE {
   carrierSCS NRSCS,
   offsetToCarrier INTEGER (0..2199, ...),
   carrierBandwidth INTEGER (0..maxnoofPhysicalResourceBlocks, ...),
   iE-Extension ProtocolExtensionContainer { {NRCarrierItem-ExtIEs} } OPTIONAL,
   ...
}

NRCarrierItem-ExtIEs F1AP-PROTOCOL-EXTENSION ::= {
   ...
}

NRFreqInfo ::= SEQUENCE {
   nRARFCN INTEGER (0..maxNRARFCN),
   sul-Information SUL-Information OPTIONAL,
   freqBandListNr SEQUENCE (SIZE(1..maxnoofNrCellBands)) OF FreqBandNrItem,
   iE-Extensions ProtocolExtensionContainer { { NRFreqInfoExtIEs} } OPTIONAL,
   ...
}

NRFreqInfoExtIEs F1AP-PROTOCOL-EXTENSION ::= {
   { ID id-FrequencyShift7p5khz CRITICALITY ignore EXTENSION FrequencyShift7p5khz PRESENCE optional },
   ...
}

NRCGI ::= SEQUENCE {
   pLMN-Identity PLMN-Identity,
   nRCellIdentity NRCellIdentity,
   iE-Extensions ProtocolExtensionContainer { {NRCGI-ExtIEs} } OPTIONAL,
   ...
}

NRCGI-ExtIEs F1AP-PROTOCOL-EXTENSION ::= {
   ...
}

NR-Mode-Info ::= CHOICE {
   fDD FDD-Info,
   tDD TDD-Info,
   choice-extension ProtocolIE-SingleContainer { { NR-Mode-Info-ExtIEs} }
}

NR-Mode-Info-ExtIEs F1AP-PROTOCOL-IES ::= {
   ...
}

NRPRACHConfig ::= SEQUENCE {
   ulPRACHConfigList NRPRACHConfigList OPTIONAL,
   sulPRACHConfigList NRPRACHConfigList OPTIONAL,
   iE-Extension ProtocolExtensionContainer { {NRPRACHConfig-ExtIEs} } OPTIONAL,
   ...
}

NRPRACHConfig-ExtIEs F1AP-PROTOCOL-EXTENSION ::= {
   ...
}

NRCellIdentity ::= BIT STRING (SIZE(36))

NRNRB ::= ENUMERATED { nrb11, nrb18, nrb24, nrb25, nrb31, nrb32,
  nrb38, nrb51, nrb52, nrb65, nrb66, nrb78, nrb79, nrb93,
  nrb106, nrb107, nrb121, nrb132, nrb133, nrb135, nrb160,
  nrb162, nrb189, nrb216, nrb217, nrb245, nrb264, nrb270, nrb273, ...}

NRPCI ::= INTEGER(0..1007)

NRPRACHConfigList ::= SEQUENCE (SIZE(0..maxnoofPRACHconfigs)) OF NRPRACHConfigItem

NRPRACHConfigItem ::= SEQUENCE {
   nRSCS NRSCS,
   prachFreqStartfromCarrier INTEGER (0..maxnoofPhysicalResourceBlocks-1, ...),
   msg1FDM ENUMERATED {one, two, four, eight, ...},
   parchConfigIndex INTEGER (0..255, ..., 256..262),
   ssb-perRACH-Occasion ENUMERATED {oneEighth, oneFourth, oneHalf, one,
      two, four, eight, sixteen, ...},
   freqDomainLength FreqDomainLength,
   zeroCorrelZoneConfig INTEGER (0..15),
   iE-Extension ProtocolExtensionContainer { { NRPRACHConfigItem-ExtIEs} } OPTIONAL,
   ...
}

NRPRACHConfigItem-ExtIEs F1AP-PROTOCOL-EXTENSION ::= {
   ...
}

NRSCS ::= ENUMERATED { scs15, scs30, scs60, scs120, ...}

NRUERLFReportContainer ::= OCTET STRING

NumberofActiveUEs ::= INTEGER(0..16777215, ...)

NumberOfBroadcasts ::= INTEGER (0..65535)

NumberofBroadcastRequest ::= INTEGER (0..65535)

NumDLULSymbols ::= SEQUENCE {
   numDLSymbols INTEGER (0..13, ...),
   numULSymbols INTEGER (0..13, ...),
   iE-Extensions ProtocolExtensionContainer { { NumDLULSymbols-ExtIEs} } OPTIONAL
}

NumDLULSymbols-ExtIEs F1AP-PROTOCOL-EXTENSION ::= {
   ...
}

NRV2XServicesAuthorized ::= SEQUENCE {
   vehicleUE VehicleUE OPTIONAL,
   pedestrianUE PedestrianUE OPTIONAL,
   iE-Extensions ProtocolExtensionContainer { {NRV2XServicesAuthorized-ExtIEs} } OPTIONAL
}

NRV2XServicesAuthorized-ExtIEs F1AP-PROTOCOL-EXTENSION ::= {
   ...
}

NRUESidelinkAggregateMaximumBitrate ::= SEQUENCE {
   uENRSidelinkAggregateMaximumBitrate BitRate,
   iE-Extensions ProtocolExtensionContainer { {NRUESidelinkAggregateMaximumBitrate-ExtIEs} } OPTIONAL
}

NRUESidelinkAggregateMaximumBitrate-ExtIEs F1AP-PROTOCOL-EXTENSION ::= {
   ...
}

NZP-CSI-RS-ResourceID::= INTEGER (0..191)

-- O

OffsetToPointA ::= INTEGER (0..2199,...)

-- P

PacketDelayBudget ::= INTEGER (0..1023, ...)

PacketErrorRate ::= SEQUENCE {
   pER-Scalar PER-Scalar,
   pER-Exponent PER-Exponent,
   iE-Extensions ProtocolExtensionContainer { {PacketErrorRate-ExtIEs} } OPTIONAL,
   ...
}

PacketErrorRate-ExtIEs F1AP-PROTOCOL-EXTENSION ::= {
   ...
}

PER-Scalar ::= INTEGER (0..9, ...)
PER-Exponent ::= INTEGER (0..9, ...)

PagingCell-Item ::= SEQUENCE {
   nRCGI NRCGI ,
   iE-Extensions ProtocolExtensionContainer { { PagingCell-ItemExtIEs } } OPTIONAL
}

PagingCell-ItemExtIEs F1AP-PROTOCOL-EXTENSION ::= {
   ...
}

PagingDRX ::= ENUMERATED {
   v32,
   v64,
   v128,
   v256,
   ...
}

PagingIdentity ::= CHOICE {
   rANUEPagingIdentity RANUEPagingIdentity,
   cNUEPagingIdentity CNUEPagingIdentity,
   choice-extension ProtocolIE-SingleContainer { { PagingIdentity-ExtIEs } }
}

PagingIdentity-ExtIEs F1AP-PROTOCOL-IES::= {
   ...
}

PagingOrigin ::= ENUMERATED { non-3gpp, ...}

PagingPriority ::= ENUMERATED { priolevel1, priolevel2, priolevel3, priolevel4, priolevel5, priolevel6, priolevel7, priolevel8,...}

RelativePathDelay ::= CHOICE {
   k0 INTEGER (0..16351),
   k1 INTEGER (0..8176),
   k2 INTEGER (0..4088),
   k3 INTEGER (0..2044),
   k4 INTEGER (0..1022),
   k5 INTEGER (0..511),
   choice-extension ProtocolIE-SingleContainer { { RelativePathDelay-ExtIEs } }
}

RelativePathDelay-ExtIEs F1AP-PROTOCOL-IES ::= {
   ...
}

PathlossReferenceInfo ::= SEQUENCE {
   pathlossReferenceSignal PathlossReferenceSignal,
   iE-Extensions ProtocolExtensionContainer { {PathlossReferenceInfo-ExtIEs} } OPTIONAL
}

PathlossReferenceInfo-ExtIEs F1AP-PROTOCOL-EXTENSION ::= {
   ...
}

PathlossReferenceSignal ::= CHOICE {
   sSB SSB,
   dL-PRS DL-PRS,
   choice-extension ProtocolIE-SingleContainer {{PathlossReferenceSignal-ExtIEs }}
}

PathlossReferenceSignal-ExtIEs F1AP-PROTOCOL-IES ::= {
   ...
}

PC5QoSFlowIdentifier ::= INTEGER (1..2048)

PC5-QoS-Characteristics ::= CHOICE {
   non-Dynamic-PQI NonDynamicPQIDescriptor,
   dynamic-PQI DynamicPQIDescriptor,
   choice-extension ProtocolIE-SingleContainer { { PC5-QoS-Characteristics-ExtIEs } }
}

PC5-QoS-Characteristics-ExtIEs F1AP-PROTOCOL-IES ::= {
   ...
}

PC5QoSParameters ::= SEQUENCE {
   pC5-QoS-Characteristics PC5-QoS-Characteristics,
   pC5-QoS-Flow-Bit-Rates PC5FlowBitRates OPTIONAL,
   iE-Extensions ProtocolExtensionContainer { { PC5QoSParameters-ExtIEs } } OPTIONAL,
   ...
}

PC5QoSParameters-ExtIEs F1AP-PROTOCOL-EXTENSION ::= {
   ...
}

PC5FlowBitRates ::= SEQUENCE {
   guaranteedFlowBitRate BitRate,
   maximumFlowBitRate BitRate,
   iE-Extensions ProtocolExtensionContainer { { PC5FlowBitRates-ExtIEs } } OPTIONAL,
   ...
}

PC5FlowBitRates-ExtIEs F1AP-PROTOCOL-EXTENSION ::= {
   ...
}

PDCCH-BlindDetectionSCG ::= OCTET STRING

PDCP-SN ::= INTEGER (0..4095)

PDCPSNLength ::= ENUMERATED { twelve-bits,eighteen-bits,...}

PDUSessionID ::= INTEGER (0..255)

ReportingPeriodicityValue ::= INTEGER (0..512, ...)

Periodicity ::= INTEGER (0..640000, ...)

PeriodicitySRS ::= ENUMERATED { ms0p125, ms0p25, ms0p5, ms0p625, ms1,
  ms1p25, ms2, ms2p5, ms4, ms5, ms8, ms10, ms16, ms20, ms32, ms40, ms64, ms80,
  ms160, ms320, ms640, ms1280, ms2560, ms5120, ms10240, ...}

PeriodicityList ::= SEQUENCE (SIZE(1.. maxnoSRS-ResourcePerSet)) OF PeriodicityList-Item

PeriodicityList-Item ::= SEQUENCE {
   periodicitySRS PeriodicitySRS,
   iE-Extensions ProtocolExtensionContainer { { PeriodicityList-ItemExtIEs} } OPTIONAL
}

PeriodicityList-ItemExtIEs F1AP-PROTOCOL-EXTENSION ::= {
   ...
}

Permutation ::= ENUMERATED {dfu, ufd, ...}

Ph-InfoMCG ::= OCTET STRING

Ph-InfoSCG ::= OCTET STRING

PLMN-Identity ::= OCTET STRING (SIZE(3))

PortNumber ::= BIT STRING (SIZE (16))

PosAssistance-Information ::= OCTET STRING

PosAssistanceInformationFailureList ::= OCTET STRING

PosBroadcast ::= ENUMERATED {
   start,
   stop,
   ...
}

PositioningBroadcastCells ::= SEQUENCE (SIZE (1..maxnoBcastCell)) OF NRCGI

MeasurementPeriodicity ::= ENUMERATED
{ms120, ms240, ms480, ms640, ms1024, ms2048, ms5120, ms10240, min1, min6, min12, min30, ..., ms20480, ms40960}

PosMeasurementQuantities ::= SEQUENCE (SIZE(1.. maxnoofPosMeas)) OF PosMeasurementQuantities-Item

PosMeasurementQuantities-Item ::= SEQUENCE {
   posMeasurementType PosMeasurementType,
   timingReportingGranularityFactor INTEGER (0..5) OPTIONAL,
   iE-Extensions ProtocolExtensionContainer { { PosMeasurementQuantities-ItemExtIEs} } OPTIONAL
}

PosMeasurementQuantities-ItemExtIEs F1AP-PROTOCOL-EXTENSION ::= {
   ...
}

PosMeasurementResult ::= SEQUENCE (SIZE (1.. maxnoofPosMeas)) OF PosMeasurementResultItem

PosMeasurementResultItem ::= SEQUENCE {
   measuredResultsValue MeasuredResultsValue,
   timeStamp TimeStamp,
   measurementQuality TRPMeasurementQuality OPTIONAL,
   measurementBeamInfo MeasurementBeamInfo OPTIONAL,
   iE-Extensions ProtocolExtensionContainer { { PosMeasurementResultItemExtIEs } } OPTIONAL
}

PosMeasurementResultItemExtIEs F1AP-PROTOCOL-EXTENSION ::= {
   ...
}

PosMeasurementResultList ::= SEQUENCE (SIZE(1.. maxNoOfMeasTRPs)) OF PosMeasurementResultList-Item

PosMeasurementResultList-Item ::= SEQUENCE {
   posMeasurementResult PosMeasurementResult,
   tRPID TRPID,
   iE-Extensions ProtocolExtensionContainer { { PosMeasurementResultList-ItemExtIEs} } OPTIONAL
}

PosMeasurementResultList-ItemExtIEs F1AP-PROTOCOL-EXTENSION ::= {
   { ID id-NRCGI CRITICALITY ignore EXTENSION NRCGI PRESENCE optional },
   ...
}

PosMeasurementType ::= ENUMERATED {
   gnb-rx-tx,
   ul-srs-rsrp,
   ul-aoa,
   ul-rtoa,
   ...
}

PosReportCharacteristics ::= ENUMERATED {
   ondemand,
   periodic,
   ...
}

PosResourceSetType ::= CHOICE {
   periodic PosResourceSetTypePR,
   semi-persistent PosResourceSetTypeSP,
   aperiodic PosResourceSetTypeAP,
   choice-extension ProtocolIE-SingleContainer {{ PosResourceSetType-ExtIEs }}
}

PosResourceSetType-ExtIEs F1AP-PROTOCOL-IES ::= {
   ...
}

PosResourceSetTypePR ::= SEQUENCE {
   posperiodicSet ENUMERATED{true, ...},
   iE-Extensions ProtocolExtensionContainer { { PosResourceSetTypePR-ExtIEs} } OPTIONAL
}

PosResourceSetTypePR-ExtIEs F1AP-PROTOCOL-EXTENSION ::= {
   ...
}

PosResourceSetTypeSP ::= SEQUENCE {
   possemi-persistentSet ENUMERATED{true, ...},
   iE-Extensions ProtocolExtensionContainer { { PosResourceSetTypeSP-ExtIEs} } OPTIONAL
}

PosResourceSetTypeSP-ExtIEs F1AP-PROTOCOL-EXTENSION ::= {
   ...
}

PosResourceSetTypeAP ::= SEQUENCE {
   sRSResourceTrigger-List INTEGER(1..3),
   iE-Extensions ProtocolExtensionContainer { { PosResourceSetTypeAP-ExtIEs} } OPTIONAL
}

PosResourceSetTypeAP-ExtIEs F1AP-PROTOCOL-EXTENSION ::= {
   ...
}

PosSRSResourceID-List ::= SEQUENCE (SIZE (1..maxnoSRS-PosResourcePerSet)) OF SRSPosResourceID

PosSRSResource-Item ::= SEQUENCE {
   srs-PosResourceId SRSPosResourceID,
   transmissionCombPos TransmissionCombPos,
   startPosition INTEGER (0..13),
   nrofSymbols ENUMERATED {n1, n2, n4, n8, n12},
   freqDomainShift INTEGER (0..268),
   c-SRS INTEGER (0..63),
   groupOrSequenceHopping ENUMERATED { neither, groupHopping, sequenceHopping },
   resourceTypePos ResourceTypePos,
   sequenceId INTEGER (0.. 65535),
   spatialRelationPos SpatialRelationPos OPTIONAL,
   iE-Extensions ProtocolExtensionContainer { { PosSRSResource-Item-ExtIEs} } OPTIONAL
}

PosSRSResource-Item-ExtIEs F1AP-PROTOCOL-EXTENSION ::= {
   ...
}

PosSRSResource-List ::= SEQUENCE (SIZE (1..maxnoSRS-PosResources)) OF PosSRSResource-Item

PosSRSResourceSet-Item ::= SEQUENCE {
   possrsResourceSetID INTEGER(0..15),
   possRSResourceID-List PosSRSResourceID-List,
   posresourceSetType PosResourceSetType,
   iE-Extensions ProtocolExtensionContainer { { PosSRSResourceSet-Item-ExtIEs} } OPTIONAL
}

PosSRSResourceSet-Item-ExtIEs F1AP-PROTOCOL-EXTENSION ::= {
   ...
}

PosSRSResourceSet-List ::= SEQUENCE (SIZE (1..maxnoSRS-PosResourceSets)) OF PosSRSResourceSet-Item

PrimaryPathIndication ::= ENUMERATED {
   true,
   false,
   ...
}

Pre-emptionCapability ::= ENUMERATED {
   shall-not-trigger-pre-emption,
   may-trigger-pre-emption
}

Pre-emptionVulnerability ::= ENUMERATED {
   not-pre-emptable,
   pre-emptable
}

PriorityLevel ::= INTEGER { spare (0), highest (1), lowest (14), no-priority (15) } (0..15)

ProtectedEUTRAResourceIndication ::= OCTET STRING

Protected-EUTRA-Resources-Item ::= SEQUENCE {
   spectrumSharingGroupID SpectrumSharingGroupID,
   eUTRACells-List EUTRACells-List,
   iE-Extensions ProtocolExtensionContainer { { Protected-EUTRA-Resources-ItemExtIEs } } OPTIONAL
}

Protected-EUTRA-Resources-ItemExtIEs F1AP-PROTOCOL-EXTENSION ::= {
   ...
}

PRSConfiguration ::= SEQUENCE {
   pRSResourceSet-List PRSResourceSet-List,
   iE-Extensions ProtocolExtensionContainer { { PRSConfiguration-ExtIEs } } OPTIONAL
}

PRSConfiguration-ExtIEs F1AP-PROTOCOL-EXTENSION ::= {
   ...
}

PRSInformationPos ::= SEQUENCE {
   pRS-IDPos INTEGER(0..255),
   pRS-Resource-Set-IDPos INTEGER(0..7),
   pRS-Resource-IDPos INTEGER(0..63) OPTIONAL,
   iE-Extensions ProtocolExtensionContainer { { PRSInformationPos-ExtIEs} } OPTIONAL
}

PRSInformationPos-ExtIEs F1AP-PROTOCOL-EXTENSION ::= {
   ...
}

Potential-SpCell-Item ::= SEQUENCE {
   potential-SpCell-ID NRCGI ,
   iE-Extensions ProtocolExtensionContainer { { Potential-SpCell-ItemExtIEs } } OPTIONAL,
   ...
}

Potential-SpCell-ItemExtIEs F1AP-PROTOCOL-EXTENSION ::= {
   ...
}

PRSAngleList ::= SEQUENCE (SIZE(1.. maxnoofPRS-ResourcesPerSet)) OF PRSAngleItem

PRSAngleItem ::= SEQUENCE {
   nR-PRS-Azimuth INTEGER (0..359),
   nR-PRS-Azimuth-fine INTEGER (0..9),
   nR-PRS-Elevation INTEGER (0..180),
   nR-PRS-Elevation-fine INTEGER (0..9),
   iE-Extensions ProtocolExtensionContainer { { PRSAngleItem-ItemExtIEs } } OPTIONAL
}

PRSAngleItem-ItemExtIEs F1AP-PROTOCOL-EXTENSION ::= {
   ...
}

PRSMuting::= SEQUENCE {
   pRSMutingOption1 PRSMutingOption1,
   pRSMutingOption2 PRSMutingOption2,
   iE-Extensions ProtocolExtensionContainer { { PRSMuting-ExtIEs} } OPTIONAL
}

PRSMuting-ExtIEs F1AP-PROTOCOL-EXTENSION ::= {
   ...
}

PRSMutingOption1 ::= SEQUENCE {
   mutingPattern DL-PRSMutingPattern,
   mutingBitRepetitionFactor ENUMERATED{rf1,rf2,rf4,rf8,...},
   iE-Extensions ProtocolExtensionContainer { { PRSMutingOption1-ExtIEs} } OPTIONAL
}

PRSMutingOption1-ExtIEs F1AP-PROTOCOL-EXTENSION ::= {
   ...
}

PRSMutingOption2 ::= SEQUENCE {
   mutingPattern DL-PRSMutingPattern,
   iE-Extensions ProtocolExtensionContainer { { PRSMutingOption2-ExtIEs} } OPTIONAL
}

PRSMutingOption2-ExtIEs F1AP-PROTOCOL-EXTENSION ::= {
   ...
}

PRS-Resource-ID ::= INTEGER (0..63)

PRSResource-List::= SEQUENCE (SIZE (1..maxnoofPRSresources)) OF PRSResource-Item

PRSResource-Item ::= SEQUENCE {
   pRSResourceID PRS-Resource-ID,
   sequenceID INTEGER(0..4095),
   rEOffset INTEGER(0..11,...),
   resourceSlotOffset INTEGER(0..511),
   resourceSymbolOffset INTEGER(0..12),
   qCLInfo PRSResource-QCLInfo OPTIONAL,
   iE-Extensions ProtocolExtensionContainer { { PRSResource-Item-ExtIEs} } OPTIONAL
}

PRSResource-Item-ExtIEs F1AP-PROTOCOL-EXTENSION ::= {
   ...
}

PRSResource-QCLInfo ::= CHOICE {
   qCLSourceSSB PRSResource-QCLSourceSSB,
   qCLSourcePRS PRSResource-QCLSourcePRS,
   choice-extension ProtocolIE-SingleContainer { { PRSResource-QCLInfo-ExtIEs } }
}
PRSResource-QCLInfo-ExtIEs F1AP-PROTOCOL-IES ::= {
   ...
}

PRSResource-QCLSourceSSB ::= SEQUENCE {
   pCI-NR INTEGER(0..1007),
   sSB-Index SSB-Index OPTIONAL,
   iE-Extensions ProtocolExtensionContainer { { PRSResource-QCLSourceSSB-ExtIEs} } OPTIONAL,
   ...
}

PRSResource-QCLSourceSSB-ExtIEs F1AP-PROTOCOL-EXTENSION ::= {
   ...
}

PRSResource-QCLSourcePRS ::= SEQUENCE {
   qCLSourcePRSResourceSetID PRS-Resource-Set-ID,
   qCLSourcePRSResourceID PRS-Resource-ID OPTIONAL,
   iE-Extensions ProtocolExtensionContainer { { PRSResource-QCLSourcePRS-ExtIEs} } OPTIONAL
}

PRSResource-QCLSourcePRS-ExtIEs F1AP-PROTOCOL-EXTENSION ::= {
   ...
}

PRS-Resource-Set-ID ::= INTEGER(0..7)

PRSResourceSet-List ::= SEQUENCE (SIZE (1.. maxnoofPRSresourceSets)) OF PRSResourceSet-Item
PRSResourceSet-Item ::= SEQUENCE {
   pRSResourceSetID PRS-Resource-Set-ID,
   subcarrierSpacing ENUMERATED{kHz15, kHz30, kHz60, kHz120, ...},
   pRSbandwidth INTEGER(1..63),
   startPRB INTEGER(0..2176),
   pointA INTEGER (0..3279165),
   combSize ENUMERATED{n2, n4, n6, n12, ...},
   cPType ENUMERATED{normal, extended, ...},
   resourceSetPeriodicity ENUMERATED{n4,n5,n8,n10,n16,n20,n32,n40,n64,n80,n160,n320,n640,n1280,n2560,n5120,n10240,n20480,n40960, n81920,...},
   resourceSetSlotOffset INTEGER(0..81919,...),
   resourceRepetitionFactor ENUMERATED{rf1,rf2,rf4,rf6,rf8,rf16,rf32,...},
   resourceTimeGap ENUMERATED{tg1,tg2,tg4,tg8,tg16,tg32,...},
   resourceNumberofSymbols ENUMERATED{n2,n4,n6,n12,...},
   pRSMuting PRSMuting OPTIONAL,
   pRSResourceTransmitPower INTEGER(-60..50),
   pRSResource-List PRSResource-List,
   iE-Extensions ProtocolExtensionContainer { { PRSResourceSet-Item-ExtIEs} } OPTIONAL
}

PRSResourceSet-Item-ExtIEs F1AP-PROTOCOL-EXTENSION ::= {
   ...
}

PWS-Failed-NR-CGI-Item ::= SEQUENCE {
   nRCGI NRCGI,
   numberOfBroadcasts NumberOfBroadcasts,
   iE-Extensions ProtocolExtensionContainer { { PWS-Failed-NR-CGI-ItemExtIEs } } OPTIONAL,
   ...
}

PWS-Failed-NR-CGI-ItemExtIEs F1AP-PROTOCOL-EXTENSION ::= {
   ...
}

PWSSystemInformation ::= SEQUENCE {
   sIBtype SIBType-PWS,
   sIBmessage OCTET STRING,
   iE-Extensions ProtocolExtensionContainer { { PWSSystemInformationExtIEs } } OPTIONAL,
   ...
}

PWSSystemInformationExtIEs F1AP-PROTOCOL-EXTENSION ::= {
   {ID id-NotificationInformation CRITICALITY ignore EXTENSION NotificationInformation PRESENCE optional}|
   { ID id-AdditionalSIBMessageList CRITICALITY reject EXTENSION AdditionalSIBMessageList PRESENCE optional},
   ...
}

PrivacyIndicator ::= ENUMERATED {immediate-MDT, logged-MDT, ...}

-- Q

QCI ::= INTEGER (0..255)

QoS-Characteristics ::= CHOICE {
   non-Dynamic-5QI NonDynamic5QIDescriptor,
   dynamic-5QI Dynamic5QIDescriptor,
   choice-extension ProtocolIE-SingleContainer { { QoS-Characteristics-ExtIEs } }
}

QoS-Characteristics-ExtIEs F1AP-PROTOCOL-IES ::= {
   ...
}

QoSFlowIdentifier ::= INTEGER (0..63)

QoSFlowLevelQoSParameters ::= SEQUENCE {
   qoS-Characteristics QoS-Characteristics,
   nGRANallocationRetentionPriority NGRANAllocationAndRetentionPriority,
   gBR-QoS-Flow-Information GBR-QoSFlowInformation OPTIONAL,
   reflective-QoS-Attribute ENUMERATED {subject-to, ...} OPTIONAL,
   iE-Extensions ProtocolExtensionContainer { { QoSFlowLevelQoSParameters-ExtIEs } } OPTIONAL
}

QoSFlowLevelQoSParameters-ExtIEs F1AP-PROTOCOL-EXTENSION ::= {
   { ID id-PDUSessionID CRITICALITY ignore EXTENSION PDUSessionID PRESENCE optional}|
   { ID id-ULPDUSessionAggregateMaximumBitRate CRITICALITY ignore EXTENSION BitRate PRESENCE optional}|
   { ID id-QosMonitoringRequest CRITICALITY ignore EXTENSION QosMonitoringRequest PRESENCE optional},
   ...
}

QoSFlowMappingIndication ::= ENUMERATED {ul,dl,...}

QoSInformation ::= CHOICE {
   eUTRANQoS EUTRANQoS,
   choice-extension ProtocolIE-SingleContainer { { QoSInformation-ExtIEs} }
}

QoSInformation-ExtIEs F1AP-PROTOCOL-IES ::= {
   { ID id-DRB-Information CRITICALITY ignore TYPE DRB-Information PRESENCE mandatory},
   ...
}

QosMonitoringRequest ::= ENUMERATED {ul, dl, both, ..., stop}

QoSParaSetIndex ::= INTEGER (1..8, ...)

QoSParaSetNotifyIndex ::= INTEGER (0..8, ...)

-- R

RACH-Config-Common ::= OCTET STRING

RACH-Config-Common-IAB ::= OCTET STRING

RACHReportContainer::= OCTET STRING

RACHReportInformationList ::= SEQUENCE (SIZE(1.. maxnoofRACHReports)) OF RACHReportInformationItem

RACHReportInformationItem ::= SEQUENCE {
   rACHReportContainer RACHReportContainer,
   uEAssitantIdentifier GNB-DU-UE-F1AP-ID OPTIONAL,
   iE-Extensions ProtocolExtensionContainer { { RACHReportInformationItem-ExtIEs} } OPTIONAL,
   ...
}

RACHReportInformationItem-ExtIEs F1AP-PROTOCOL-EXTENSION ::= {
   ...
}

RadioResourceStatus ::= SEQUENCE {
   sSBAreaRadioResourceStatusList SSBAreaRadioResourceStatusList,
   iE-Extensions ProtocolExtensionContainer { { RadioResourceStatus-ExtIEs} } OPTIONAL
}

RadioResourceStatus-ExtIEs F1AP-PROTOCOL-EXTENSION ::= {
   ...
}

RANAC ::= INTEGER (0..255)

RAN-MeasurementID ::= INTEGER (1.. 65536, ...)

RAN-UE-MeasurementID ::= INTEGER (1.. 256, ...)

RANUEID ::= OCTET STRING (SIZE (8))

RANUEPagingIdentity ::= SEQUENCE {
   iRNTI BIT STRING (SIZE(40)),
iE-Extensions ProtocolExtensionContainer { { RANUEPagingIdentity-ExtIEs } } OPTIONAL}

RANUEPagingIdentity-ExtIEs F1AP-PROTOCOL-EXTENSION ::= {
   ...
}

RAT-FrequencyPriorityInformation::= CHOICE {
   eNDC SubscriberProfileIDforRFP,
   nGRAN RAT-FrequencySelectionPriority,
   choice-extension ProtocolIE-SingleContainer { { RAT-FrequencyPriorityInformation-ExtIEs} }
}

RAT-FrequencyPriorityInformation-ExtIEs F1AP-PROTOCOL-IES ::= {
   ...
}

RAT-FrequencySelectionPriority::= INTEGER (1.. 256, ...)

Reestablishment-Indication ::= ENUMERATED {
   reestablished,
   ...
}

ReferencePoint ::= CHOICE {
   coordinateID CoordinateID,
   referencePointCoordinate AccessPointPosition,
   referencePointCoordinateHA NGRANHighAccuracyAccessPointPosition,
   choice-Extension ProtocolIE-SingleContainer { { ReferencePoint-ExtIEs} }
}

ReferencePoint-ExtIEs F1AP-PROTOCOL-IES ::= {
   ...
}

ReferenceSFN ::= INTEGER (0..1023)

ReferenceSignal ::= CHOICE {
   nZP-CSI-RS NZP-CSI-RS-ResourceID,
   sSB SSB,
   sRS SRSResourceID,
   positioningSRS SRSPosResourceID,
   dL-PRS DL-PRS,
   choice-extension ProtocolIE-SingleContainer {{ReferenceSignal-ExtIEs }}
}

ReferenceSignal-ExtIEs F1AP-PROTOCOL-IES ::= {
   ...
}

RelativeCartesianLocation ::= SEQUENCE {
   xYZunit ENUMERATED {mm, cm, dm, ...},
   xvalue INTEGER (-65536..65535),
   yvalue INTEGER (-65536..65535),
   zvalue INTEGER (-32768..32767),
   locationUncertainty LocationUncertainty,
   iE-Extensions ProtocolExtensionContainer { { RelativeCartesianLocation-ExtIEs} } OPTIONAL
}

RelativeCartesianLocation-ExtIEs F1AP-PROTOCOL-EXTENSION ::= {
   ...
}

RelativeGeodeticLocation ::= SEQUENCE {
   milli-Arc-SecondUnits ENUMERATED {zerodot03, zerodot3, three, ...},
   heightUnits ENUMERATED {mm, cm, m, ...},
   deltaLatitude INTEGER (-1024.. 1023),
   deltaLongitude INTEGER (-1024.. 1023),
   deltaHeight INTEGER (-1024.. 1023),
   locationUncertainty LocationUncertainty,
   iE-extensions ProtocolExtensionContainer {{RelativeGeodeticLocation-ExtIEs }} OPTIONAL
}

RelativeGeodeticLocation-ExtIEs F1AP-PROTOCOL-EXTENSION ::= {
   ...
}

ReferenceTime ::= OCTET STRING

RegistrationRequest ::= ENUMERATED{start, stop, add, ...}

ReportCharacteristics ::= BIT STRING (SIZE(32))

ReportingPeriodicity ::= ENUMERATED{ms500, ms1000, ms2000, ms5000, ms10000, ...}

RequestedBandCombinationIndex ::= OCTET STRING

RequestedFeatureSetEntryIndex ::= OCTET STRING

RequestedP-MaxFR2 ::= OCTET STRING

Requested-PDCCH-BlindDetectionSCG ::= OCTET STRING

RequestedSRSTransmissionCharacteristics ::= SEQUENCE {
   numberOfTransmissions INTEGER (0..500, ...) OPTIONAL,
   -- The IE shall be present if the Resource Type IE is set to “periodic” --
   resourceType ENUMERATED {periodic, semi-persistent, aperiodic,...},
   bandwidthSRS BandwidthSRS,
   sRSResourceSetList SRSResourceSetList OPTIONAL,
   sSBInformation SSBInformation OPTIONAL,
   iE-Extensions ProtocolExtensionContainer { { RequestedSRSTransmissionCharacteristics-ExtIEs} } OPTIONAL
}

RequestedSRSTransmissionCharacteristics-ExtIEs F1AP-PROTOCOL-EXTENSION ::= {
   { ID id-SrsFrequency CRITICALITY ignore EXTENSION SrsFrequency PRESENCE optional },
   ...
}

RequestType ::= ENUMERATED {offer, execution, ...}

ResourceCoordinationEUTRACellInfo ::= SEQUENCE {
   eUTRA-Mode-Info EUTRA-Coex-Mode-Info,
   eUTRA-PRACH-Configuration EUTRA-PRACH-Configuration,
   iE-Extensions ProtocolExtensionContainer { { ResourceCoordinationEUTRACellInfo-ExtIEs } } OPTIONAL,
   ...
}

ResourceCoordinationEUTRACellInfo-ExtIEs F1AP-PROTOCOL-EXTENSION ::= {
   {ID id-IgnorePRACHConfiguration CRITICALITY reject EXTENSION IgnorePRACHConfiguration PRESENCE optional },
   ...
}

ResourceCoordinationTransferInformation ::= SEQUENCE {
   meNB-Cell-ID EUTRA-Cell-ID,
   resourceCoordinationEUTRACellInfo ResourceCoordinationEUTRACellInfo OPTIONAL,
   iE-Extensions ProtocolExtensionContainer { { ResourceCoordinationTransferInformation-ExtIEs } } OPTIONAL,
   ...
}

ResourceCoordinationTransferInformation-ExtIEs F1AP-PROTOCOL-EXTENSION ::= {
   ...
}

ResourceCoordinationTransferContainer ::= OCTET STRING

ResourceSetType ::= CHOICE {
   periodic ResourceSetTypePeriodic,
   semi-persistent ResourceSetTypeSemi-persistent,
   aperiodic ResourceSetTypeAperiodic,
   choice-extension ProtocolIE-SingleContainer {{ ResourceSetType-ExtIEs }}
}

ResourceSetType-ExtIEs F1AP-PROTOCOL-IES ::= {
   ...
}

ResourceSetTypePeriodic ::= SEQUENCE {
   periodicSet ENUMERATED{true, ...},
   iE-Extensions ProtocolExtensionContainer { { ResourceSetTypePeriodic-ExtIEs} } OPTIONAL
}

ResourceSetTypePeriodic-ExtIEs F1AP-PROTOCOL-EXTENSION ::= {
   ...
}

ResourceSetTypeSemi-persistent ::= SEQUENCE {
   semi-persistentSet ENUMERATED{true, ...},
   iE-Extensions ProtocolExtensionContainer { { ResourceSetTypeSemi-persistent-ExtIEs} } OPTIONAL
}

ResourceSetTypeSemi-persistent-ExtIEs F1AP-PROTOCOL-EXTENSION ::= {
   ...
}

ResourceSetTypeAperiodic ::= SEQUENCE {
   sRSResourceTrigger-List INTEGER(1..3),
   slotoffset INTEGER(0..32),
   iE-Extensions ProtocolExtensionContainer { { ResourceSetTypeAperiodic-ExtIEs} } OPTIONAL
}

ResourceSetTypeAperiodic-ExtIEs F1AP-PROTOCOL-EXTENSION ::= {
   ...
}

RepetitionPeriod ::= INTEGER (0..131071, ...)

ReportingRequestType ::= SEQUENCE {
   eventType EventType,
   reportingPeriodicityValue ReportingPeriodicityValue OPTIONAL,
   -- C-ifEventTypeisPeriodic: This IE shall be present if the Event Type IE is set to "periodic" in the Event Type IE.
   iE-Extensions ProtocolExtensionContainer { {ReportingRequestType-ExtIEs} } OPTIONAL
}

ReportingRequestType-ExtIEs F1AP-PROTOCOL-EXTENSION ::= {
   ...
}

ResourceType ::= CHOICE {
   periodic ResourceTypePeriodic,
   semi-persistent ResourceTypeSemi-persistent,
   aperiodic ResourceTypeAperiodic,
   choice-extension ProtocolIE-SingleContainer {{ ResourceType-ExtIEs }}
}

ResourceType-ExtIEs F1AP-PROTOCOL-IES ::= {
   ...
}

ResourceTypePeriodic ::= SEQUENCE {
   periodicity ENUMERATED{slot1, slot2, slot4, slot5, slot8, slot10,
     slot16, slot20, slot32, slot40, slot64, slot80, slot160, slot320, slot640, slot1280, slot2560, ...},
   offset INTEGER(0..2559, ...),
   iE-Extensions ProtocolExtensionContainer { { ResourceTypePeriodic-ExtIEs} } OPTIONAL
}

ResourceTypePeriodic-ExtIEs F1AP-PROTOCOL-EXTENSION ::= {
   ...
}

ResourceTypeSemi-persistent ::= SEQUENCE {
   periodicity ENUMERATED{slot1, slot2, slot4, slot5, slot8, slot10,
     slot16, slot20, slot32, slot40, slot64, slot80, slot160, slot320, slot640, slot1280, slot2560, ...},
   offset INTEGER(0..2559, ...),
   iE-Extensions ProtocolExtensionContainer { { ResourceTypeSemi-persistent-ExtIEs} } OPTIONAL
}

ResourceTypeSemi-persistent-ExtIEs F1AP-PROTOCOL-EXTENSION ::= {
   ...
}

ResourceTypeAperiodic ::= SEQUENCE {
   aperiodicResourceType ENUMERATED{true, ...},
   iE-Extensions ProtocolExtensionContainer { { ResourceTypeAperiodic-ExtIEs} } OPTIONAL
}

ResourceTypeAperiodic-ExtIEs F1AP-PROTOCOL-EXTENSION ::= {
   ...
}

ResourceTypePos ::= CHOICE {
   periodic ResourceTypePeriodicPos,
   semi-persistent ResourceTypeSemi-persistentPos,
   aperiodic ResourceTypeAperiodicPos,
   choice-extension ProtocolIE-SingleContainer {{ ResourceTypePos-ExtIEs }}
}

ResourceTypePos-ExtIEs F1AP-PROTOCOL-IES ::= {
   ...
}

ResourceTypePeriodicPos ::= SEQUENCE {
   periodicity ENUMERATED{slot1, slot2, slot4, slot5, slot8, slot10,
     slot16, slot20, slot32, slot40, slot64, slot80, slot160, slot320, slot640,
     slot1280, slot2560, slot5120, slot10240, slot40960, slot81920, ...},
   offset INTEGER(0..81919, ...),
   iE-Extensions ProtocolExtensionContainer { { ResourceTypePeriodicPos-ExtIEs} } OPTIONAL
}

ResourceTypePeriodicPos-ExtIEs F1AP-PROTOCOL-EXTENSION ::= {
   ...
}

ResourceTypeSemi-persistentPos ::= SEQUENCE {
   periodicity ENUMERATED{slot1, slot2, slot4, slot5, slot8, slot10,
     slot16, slot20, slot32, slot40, slot64, slot80, slot160, slot320, slot640,
     slot1280, slot2560, slot5120, slot10240, slot40960, slot81920, ...},
   offset INTEGER(0..81919, ...),
   iE-Extensions ProtocolExtensionContainer { { ResourceTypeSemi-persistentPos-ExtIEs} } OPTIONAL
}

ResourceTypeSemi-persistentPos-ExtIEs F1AP-PROTOCOL-EXTENSION ::= {
   ...
}

ResourceTypeAperiodicPos ::= SEQUENCE {
   slotOffset INTEGER (0..32),
   iE-Extensions ProtocolExtensionContainer { { ResourceTypeAperiodicPos-ExtIEs} } OPTIONAL
}

ResourceTypeAperiodicPos-ExtIEs F1AP-PROTOCOL-EXTENSION ::= {
   ...
}

RLCDuplicationInformation ::= SEQUENCE {
   rLCDuplicationStateList RLCDuplicationStateList,
   primaryPathIndication PrimaryPathIndication OPTIONAL,
   iE-Extensions ProtocolExtensionContainer { {RLCDuplicationInformation-ExtIEs} } OPTIONAL
}

RLCDuplicationInformation-ExtIEs F1AP-PROTOCOL-EXTENSION ::= {
   ...
}

RLCDuplicationStateList ::= SEQUENCE (SIZE(1..maxnoofRLCDuplicationState)) OF RLCDuplicationState-Item

RLCDuplicationState-Item ::=SEQUENCE {
   duplicationState DuplicationState,
   iE-Extensions ProtocolExtensionContainer { {RLCDuplicationState-Item-ExtIEs } } OPTIONAL,
   ...
}

RLCDuplicationState-Item-ExtIEs F1AP-PROTOCOL-EXTENSION ::= {
   ...
}

RLCFailureIndication ::= SEQUENCE {
   assocatedLCID LCID,
   iE-Extensions ProtocolExtensionContainer { {RLCFailureIndication-ExtIEs} } OPTIONAL
}

RLCFailureIndication-ExtIEs F1AP-PROTOCOL-EXTENSION ::= {
   ...
}

RLCMode ::= ENUMERATED {
   rlc-am,
   rlc-um-bidirectional,
   rlc-um-unidirectional-ul,
   rlc-um-unidirectional-dl,
   ...
}

RLC-Status ::= SEQUENCE {
   reestablishment-Indication Reestablishment-Indication,
   iE-Extensions ProtocolExtensionContainer { { RLC-Status-ExtIEs } } OPTIONAL,
   ...
}

RLC-Status-ExtIEs F1AP-PROTOCOL-EXTENSION ::= {
   ...
}

RLFReportInformationList ::= SEQUENCE (SIZE(1.. maxnoofRLFReports)) OF RLFReportInformationItem

RLFReportInformationItem ::= SEQUENCE {
   nRUERLFReportContainer NRUERLFReportContainer,
   uEAssitantIdentifier GNB-DU-UE-F1AP-ID OPTIONAL,
   iE-Extensions ProtocolExtensionContainer { { RLFReportInformationItem-ExtIEs} } OPTIONAL,
   ...
}

RLFReportInformationItem-ExtIEs F1AP-PROTOCOL-EXTENSION ::= {
   ...
}

RIMRSDetectionStatus ::= ENUMERATED {rs-detected, rs-disappeared, ...}

RRCContainer ::= OCTET STRING

RRCContainer-RRCSetupComplete ::= OCTET STRING

RRCDeliveryStatus ::= SEQUENCE {
   delivery-status PDCP-SN,
   triggering-message PDCP-SN,
iE-Extensions ProtocolExtensionContainer { { RRCDeliveryStatus-ExtIEs } } OPTIONAL}

RRCDeliveryStatus-ExtIEs F1AP-PROTOCOL-EXTENSION ::= {
   ...
}

RRCDeliveryStatusRequest ::= ENUMERATED {true, ...}

RRCReconfigurationCompleteIndicator ::= ENUMERATED {
   true,
   ...,
   failure
}

RRC-Version ::= SEQUENCE {
   latest-RRC-Version BIT STRING (SIZE(3)),
iE-Extensions ProtocolExtensionContainer { { RRC-Version-ExtIEs } } OPTIONAL}

RRC-Version-ExtIEs F1AP-PROTOCOL-EXTENSION ::= {
   {ID id-latest-RRC-Version-Enhanced CRITICALITY ignore EXTENSION OCTET STRING (SIZE(3)) PRESENCE optional },
   ...
}

RoutingID ::= OCTET STRING

-- S

SCell-FailedtoSetup-Item ::= SEQUENCE {
   sCell-ID NRCGI ,
   cause Cause OPTIONAL ,
   iE-Extensions ProtocolExtensionContainer { { SCell-FailedtoSetup-ItemExtIEs } } OPTIONAL,
   ...
}

SCell-FailedtoSetup-ItemExtIEs F1AP-PROTOCOL-EXTENSION ::= {
   ...
}

SCell-FailedtoSetupMod-Item ::= SEQUENCE {
   sCell-ID NRCGI ,
   cause Cause OPTIONAL ,
   iE-Extensions ProtocolExtensionContainer { { SCell-FailedtoSetupMod-ItemExtIEs } } OPTIONAL,
   ...
}

SCell-FailedtoSetupMod-ItemExtIEs F1AP-PROTOCOL-EXTENSION ::= {
   ...
}

SCell-ToBeRemoved-Item ::= SEQUENCE {
   sCell-ID NRCGI ,
   iE-Extensions ProtocolExtensionContainer { { SCell-ToBeRemoved-ItemExtIEs } } OPTIONAL,
   ...
}

SCell-ToBeRemoved-ItemExtIEs F1AP-PROTOCOL-EXTENSION ::= {
   ...
}

SCell-ToBeSetup-Item ::= SEQUENCE {
   sCell-ID NRCGI ,
   sCellIndex SCellIndex,
   sCellULConfigured CellULConfigured OPTIONAL,
   iE-Extensions ProtocolExtensionContainer { { SCell-ToBeSetup-ItemExtIEs } } OPTIONAL,
   ...
}

SCell-ToBeSetup-ItemExtIEs F1AP-PROTOCOL-EXTENSION ::= {
   { ID id-ServingCellMO CRITICALITY ignore EXTENSION ServingCellMO PRESENCE optional },
   ...
}

SCell-ToBeSetupMod-Item ::= SEQUENCE {
   sCell-ID NRCGI ,
   sCellIndex SCellIndex,
   sCellULConfigured CellULConfigured OPTIONAL,
   iE-Extensions ProtocolExtensionContainer { { SCell-ToBeSetupMod-ItemExtIEs } } OPTIONAL,
   ...
}

SCell-ToBeSetupMod-ItemExtIEs F1AP-PROTOCOL-EXTENSION ::= {
   { ID id-ServingCellMO CRITICALITY ignore EXTENSION ServingCellMO PRESENCE optional },
   ...
}

SCellIndex ::=INTEGER (1..31, ...)

SCGIndicator ::= ENUMERATED{released, ...}

SCS-SpecificCarrier ::= SEQUENCE {
   offsetToCarrier INTEGER (0..2199,...),
   subcarrierSpacing ENUMERATED {kHz15, kHz30, kHz60, kHz120,...},
   carrierBandwidth INTEGER (1..275,...),
   iE-Extensions ProtocolExtensionContainer { { SCS-SpecificCarrier-ExtIEs } } OPTIONAL
}

SCS-SpecificCarrier-ExtIEs F1AP-PROTOCOL-EXTENSION ::= {
   ...
}

Search-window-information ::= SEQUENCE {
   expectedPropagationDelay INTEGER (-3841..3841,...),
   delayUncertainty INTEGER (1..246,...),
   iE-Extensions ProtocolExtensionContainer { { Search-window-information-ExtIEs } } OPTIONAL
}

Search-window-information-ExtIEs F1AP-PROTOCOL-EXTENSION ::= {
   ...
}

SerialNumber ::= BIT STRING (SIZE (16))

SIBType-PWS ::=INTEGER (6..8, ...)

SelectedBandCombinationIndex ::= OCTET STRING

SelectedFeatureSetEntryIndex ::= OCTET STRING

CG-ConfigInfo ::= OCTET STRING

ServCellIndex ::= INTEGER (0..31, ...)

ServingCellMO ::= INTEGER (1..64, ...)

Served-Cell-Information ::= SEQUENCE {
   nRCGI NRCGI,
   nRPCI NRPCI,
   fiveGS-TAC FiveGS-TAC OPTIONAL,
   configured-EPS-TAC Configured-EPS-TAC OPTIONAL,
   servedPLMNs ServedPLMNs-List,
   nR-Mode-Info NR-Mode-Info,
   measurementTimingConfiguration OCTET STRING,
   iE-Extensions ProtocolExtensionContainer { {Served-Cell-Information-ExtIEs} } OPTIONAL,
   ...
}

Served-Cell-Information-ExtIEs F1AP-PROTOCOL-EXTENSION ::= {
   { ID id-RANAC CRITICALITY ignore EXTENSION RANAC PRESENCE optional }|
   { ID id-ExtendedServedPLMNs-List CRITICALITY ignore EXTENSION ExtendedServedPLMNs-List PRESENCE optional }|
   { ID id-Cell-Direction CRITICALITY ignore EXTENSION Cell-Direction PRESENCE optional }|
   { ID id-BPLMN-ID-Info-List CRITICALITY ignore EXTENSION BPLMN-ID-Info-List PRESENCE optional }|
   { ID id-Cell-Type CRITICALITY ignore EXTENSION CellType PRESENCE optional}|
   { ID id-ConfiguredTACIndication CRITICALITY ignore EXTENSION ConfiguredTACIndication PRESENCE optional }|
   { ID id-AggressorgNBSetID CRITICALITY ignore EXTENSION AggressorgNBSetID PRESENCE optional}|
   { ID id-VictimgNBSetID CRITICALITY ignore EXTENSION VictimgNBSetID PRESENCE optional}|
   { ID id-IAB-Info-IAB-DU CRITICALITY ignore EXTENSION IAB-Info-IAB-DU PRESENCE optional}|
   { ID id-SSB-PositionsInBurst CRITICALITY ignore EXTENSION SSB-PositionsInBurst PRESENCE optional }|
   { ID id-NRPRACHConfig CRITICALITY ignore EXTENSION NRPRACHConfig PRESENCE optional }|
   { ID id-SFN-Offset CRITICALITY ignore EXTENSION SFN-Offset PRESENCE optional }|
   { ID id-NPNBroadcastInformation CRITICALITY reject EXTENSION NPNBroadcastInformation PRESENCE optional },
   ...
}

SFN-Offset ::= SEQUENCE {
   sFN-Time-Offset BIT STRING (SIZE(24)),
   iE-Extensions ProtocolExtensionContainer { {SFN-Offset-ExtIEs} } OPTIONAL,
   ...
}

SFN-Offset-ExtIEs F1AP-PROTOCOL-EXTENSION ::= {
   ...
}

Served-Cells-To-Add-Item ::= SEQUENCE {
   served-Cell-Information Served-Cell-Information,
   gNB-DU-System-Information GNB-DU-System-Information OPTIONAL,
   iE-Extensions ProtocolExtensionContainer { { Served-Cells-To-Add-ItemExtIEs} } OPTIONAL,
   ...
}

Served-Cells-To-Add-ItemExtIEs F1AP-PROTOCOL-EXTENSION ::= {
   ...
}

Served-Cells-To-Delete-Item ::= SEQUENCE {
   oldNRCGI NRCGI ,
   iE-Extensions ProtocolExtensionContainer { { Served-Cells-To-Delete-ItemExtIEs } } OPTIONAL,
   ...
}

Served-Cells-To-Delete-ItemExtIEs F1AP-PROTOCOL-EXTENSION ::= {
   ...
}

Served-Cells-To-Modify-Item ::= SEQUENCE {
   oldNRCGI NRCGI ,
   served-Cell-Information Served-Cell-Information ,
   gNB-DU-System-Information GNB-DU-System-Information OPTIONAL ,
   iE-Extensions ProtocolExtensionContainer { { Served-Cells-To-Modify-ItemExtIEs } } OPTIONAL,
   ...
}

Served-Cells-To-Modify-ItemExtIEs F1AP-PROTOCOL-EXTENSION ::= {
   ...
}

Served-EUTRA-Cells-Information::= SEQUENCE {
   eUTRA-Mode-Info EUTRA-Mode-Info,
   protectedEUTRAResourceIndication ProtectedEUTRAResourceIndication,
   iE-Extensions ProtocolExtensionContainer { {Served-EUTRA-Cell-Information-ExtIEs} } OPTIONAL,
   ...
}

Served-EUTRA-Cell-Information-ExtIEs F1AP-PROTOCOL-EXTENSION ::= {
   ...
}

Service-State ::= ENUMERATED {
   in-service,
   out-of-service,
   ...
}

Service-Status ::= SEQUENCE {
   service-state Service-State,
   switchingOffOngoing ENUMERATED {true, ...} OPTIONAL,
   iE-Extensions ProtocolExtensionContainer { { Service-Status-ExtIEs } } OPTIONAL,
   ...
}

Service-Status-ExtIEs F1AP-PROTOCOL-EXTENSION ::= {
   ...
}

RelativeTime1900 ::= BIT STRING (SIZE (64))

ShortDRXCycleLength ::= ENUMERATED {ms2, ms3, ms4, ms5, ms6, ms7, ms8, ms10,
  ms14, ms16, ms20, ms30, ms32, ms35, ms40, ms64, ms80,
  ms128, ms160, ms256, ms320, ms512, ms640, ...}

ShortDRXCycleTimer ::= INTEGER (1..16)

SIB1-message ::= OCTET STRING

SIB10-message ::= OCTET STRING

SIB12-message ::= OCTET STRING

SIB13-message ::= OCTET STRING

SIB14-message ::= OCTET STRING

SItype ::= INTEGER (1..32, ...)

SItype-List ::= SEQUENCE (SIZE(1.. maxnoofSITypes)) OF SItype-Item

SItype-Item ::= SEQUENCE {
   sItype SItype ,
   iE-Extensions ProtocolExtensionContainer { { SItype-ItemExtIEs } } OPTIONAL
}

SItype-ItemExtIEs F1AP-PROTOCOL-EXTENSION ::= {
   ...
}

SibtypetobeupdatedListItem ::= SEQUENCE {
   sIBtype INTEGER (2..32,...),
   sIBmessage OCTET STRING,
   valueTag INTEGER (0..31,...),
   iE-Extensions ProtocolExtensionContainer { { SibtypetobeupdatedListItem-ExtIEs } } OPTIONAL,
   ...
}

SibtypetobeupdatedListItem-ExtIEs F1AP-PROTOCOL-EXTENSION ::= {
   {ID id-areaScope CRITICALITY ignore EXTENSION AreaScope PRESENCE optional},
   ...
}

SLDRBID ::= INTEGER (1..512, ...)

SLDRBInformation ::= SEQUENCE {
   sLDRB-QoS PC5QoSParameters,
   flowsMappedToSLDRB-List FlowsMappedToSLDRB-List,
   ...
}

SLDRBs-FailedToBeModified-Item ::= SEQUENCE {
   sLDRBID SLDRBID ,
   cause Cause OPTIONAL,
   iE-Extensions ProtocolExtensionContainer { { SLDRBs-FailedToBeModified-ItemExtIEs } } OPTIONAL
}

SLDRBs-FailedToBeModified-ItemExtIEs F1AP-PROTOCOL-EXTENSION ::= {
   ...
}

SLDRBs-FailedToBeSetup-Item ::= SEQUENCE {
   sLDRBID SLDRBID,
   cause Cause OPTIONAL,
   iE-Extensions ProtocolExtensionContainer { { SLDRBs-FailedToBeSetup-ItemExtIEs } } OPTIONAL
}

SLDRBs-FailedToBeSetup-ItemExtIEs F1AP-PROTOCOL-EXTENSION ::= {
   ...
}

SLDRBs-FailedToBeSetupMod-Item ::= SEQUENCE {
   sLDRBID SLDRBID ,
   cause Cause OPTIONAL ,
   iE-Extensions ProtocolExtensionContainer { { SLDRBs-FailedToBeSetupMod-ItemExtIEs } } OPTIONAL
}

SLDRBs-FailedToBeSetupMod-ItemExtIEs F1AP-PROTOCOL-EXTENSION ::= {
   ...
}

SLDRBs-Modified-Item ::= SEQUENCE {
   sLDRBID SLDRBID,
   iE-Extensions ProtocolExtensionContainer { { SLDRBs-Modified-ItemExtIEs } } OPTIONAL
}

SLDRBs-Modified-ItemExtIEs F1AP-PROTOCOL-EXTENSION ::= {
   ...
}

SLDRBs-ModifiedConf-Item ::= SEQUENCE {
   sLDRBID SLDRBID,
   iE-Extensions ProtocolExtensionContainer { { SLDRBs-ModifiedConf-ItemExtIEs } } OPTIONAL
}

SLDRBs-ModifiedConf-ItemExtIEs F1AP-PROTOCOL-EXTENSION ::= {
   ...
}

SLDRBs-Required-ToBeModified-Item ::= SEQUENCE {
   sLDRBID SLDRBID,
   iE-Extensions ProtocolExtensionContainer { { SLDRBs-Required-ToBeModified-ItemExtIEs } } OPTIONAL
}

SLDRBs-Required-ToBeModified-ItemExtIEs F1AP-PROTOCOL-EXTENSION ::= {
   ...
}

SLDRBs-Required-ToBeReleased-Item ::= SEQUENCE {
   sLDRBID SLDRBID,
   iE-Extensions ProtocolExtensionContainer { { SLDRBs-Required-ToBeReleased-ItemExtIEs } } OPTIONAL
}

SLDRBs-Required-ToBeReleased-ItemExtIEs F1AP-PROTOCOL-EXTENSION ::= {
   ...
}

SLDRBs-Setup-Item ::= SEQUENCE {
   sLDRBID SLDRBID,
   iE-Extensions ProtocolExtensionContainer { { SLDRBs-Setup-ItemExtIEs } } OPTIONAL
}

SLDRBs-Setup-ItemExtIEs F1AP-PROTOCOL-EXTENSION ::= {
   ...
}

SLDRBs-SetupMod-Item ::= SEQUENCE {
   sLDRBID SLDRBID,
   iE-Extensions ProtocolExtensionContainer { { SLDRBs-SetupMod-ItemExtIEs } } OPTIONAL
}

SLDRBs-SetupMod-ItemExtIEs F1AP-PROTOCOL-EXTENSION ::= {
   ...
}

SLDRBs-ToBeModified-Item ::= SEQUENCE {
   sLDRBID SLDRBID,
   sLDRBInformation SLDRBInformation OPTIONAL,
   rLCMode RLCMode OPTIONAL,
   iE-Extensions ProtocolExtensionContainer { { SLDRBs-ToBeModified-ItemExtIEs } } OPTIONAL
}

SLDRBs-ToBeModified-ItemExtIEs F1AP-PROTOCOL-EXTENSION ::= {
   ...
}

SLDRBs-ToBeReleased-Item ::= SEQUENCE {
   sLDRBID SLDRBID,
   iE-Extensions ProtocolExtensionContainer { { SLDRBs-ToBeReleased-ItemExtIEs } } OPTIONAL
}

SLDRBs-ToBeReleased-ItemExtIEs F1AP-PROTOCOL-EXTENSION ::= {
   ...
}

SLDRBs-ToBeSetup-Item ::= SEQUENCE {
   sLDRBID SLDRBID,
   sLDRBInformation SLDRBInformation,
   rLCMode RLCMode,

   iE-Extensions ProtocolExtensionContainer { { SLDRBs-ToBeSetup-ItemExtIEs } } OPTIONAL
}

SLDRBs-ToBeSetup-ItemExtIEs F1AP-PROTOCOL-EXTENSION ::= {
   ...
}

SLDRBs-ToBeSetupMod-Item ::= SEQUENCE {
   sLDRBID SLDRBID,
   sLDRBInformation SLDRBInformation,
   rLCMode RLCMode OPTIONAL,
   iE-Extensions ProtocolExtensionContainer { { SLDRBs-ToBeSetupMod-ItemExtIEs } } OPTIONAL
}

SLDRBs-ToBeSetupMod-ItemExtIEs F1AP-PROTOCOL-EXTENSION ::= {
   ...
}

SL-PHY-MAC-RLC-Config ::= OCTET STRING

SL-ConfigDedicatedEUTRA-Info ::= OCTET STRING

SliceAvailableCapacity ::= SEQUENCE {
   sliceAvailableCapacityList SliceAvailableCapacityList,
   iE-Extensions ProtocolExtensionContainer { { SliceAvailableCapacity-ExtIEs} } OPTIONAL
}

SliceAvailableCapacity-ExtIEs F1AP-PROTOCOL-EXTENSION ::= {
   ...
}

SliceAvailableCapacityList ::= SEQUENCE (SIZE(1.. maxnoofBPLMNsNR)) OF SliceAvailableCapacityItem

SliceAvailableCapacityItem ::= SEQUENCE {
   pLMNIdentity PLMN-Identity,
   sNSSAIAvailableCapacity-List SNSSAIAvailableCapacity-List,
   iE-Extensions ProtocolExtensionContainer { { SliceAvailableCapacityItem-ExtIEs} } OPTIONAL
}

SliceAvailableCapacityItem-ExtIEs F1AP-PROTOCOL-EXTENSION ::= {
   ...
}

SNSSAIAvailableCapacity-List ::= SEQUENCE (SIZE(1.. maxnoofSliceItems)) OF SNSSAIAvailableCapacity-Item

SNSSAIAvailableCapacity-Item ::= SEQUENCE {
   sNSSAI SNSSAI,
   sliceAvailableCapacityValueDownlink INTEGER (0..100) OPTIONAL,
   sliceAvailableCapacityValueUplink INTEGER (0..100) OPTIONAL,
   iE-Extensions ProtocolExtensionContainer { { SNSSAIAvailableCapacity-Item-ExtIEs } } OPTIONAL
}

SNSSAIAvailableCapacity-Item-ExtIEs F1AP-PROTOCOL-EXTENSION ::= {
   ...
}

SliceSupportList ::= SEQUENCE (SIZE(1.. maxnoofSliceItems)) OF SliceSupportItem

SliceSupportItem ::= SEQUENCE {
   sNSSAI SNSSAI,
   iE-Extensions ProtocolExtensionContainer { { SliceSupportItem-ExtIEs } } OPTIONAL
}

SliceSupportItem-ExtIEs F1AP-PROTOCOL-EXTENSION ::= {
   ...
}

SliceToReportList ::= SEQUENCE (SIZE(1.. maxnoofBPLMNsNR)) OF SliceToReportItem

SliceToReportItem ::= SEQUENCE {
   pLMNIdentity PLMN-Identity,
   sNSSAIlist SNSSAI-list,
   iE-Extensions ProtocolExtensionContainer { { SliceToReportItem-ExtIEs} } OPTIONAL
}

SliceToReportItem-ExtIEs F1AP-PROTOCOL-EXTENSION ::= {
   ...
}

SlotNumber ::= INTEGER (0..79)

SNSSAI-list ::= SEQUENCE (SIZE(1.. maxnoofSliceItems)) OF SNSSAI-Item

SNSSAI-Item ::= SEQUENCE {
   sNSSAI SNSSAI,
   iE-Extensions ProtocolExtensionContainer { { SNSSAI-Item-ExtIEs } } OPTIONAL
}

SNSSAI-Item-ExtIEs F1AP-PROTOCOL-EXTENSION ::= {
   ...
}

Slot-Configuration-List ::= SEQUENCE (SIZE(1.. maxnoofslots)) OF Slot-Configuration-Item

Slot-Configuration-Item ::= SEQUENCE {
   slotIndex INTEGER (0..5119, ...),
   symbolAllocInSlot SymbolAllocInSlot,
   iE-Extensions ProtocolExtensionContainer { { Slot-Configuration-ItemExtIEs } } OPTIONAL
}

Slot-Configuration-ItemExtIEs F1AP-PROTOCOL-EXTENSION ::= {
   ...
}

SNSSAI ::= SEQUENCE {
   sST OCTET STRING (SIZE(1)),
   sD OCTET STRING (SIZE(3)) OPTIONAL ,
   iE-Extensions ProtocolExtensionContainer { { SNSSAI-ExtIEs } } OPTIONAL
}

SNSSAI-ExtIEs F1AP-PROTOCOL-EXTENSION ::= {
   ...
}

SpatialDirectionInformation ::= SEQUENCE {
   nR-PRSBeamInformation NR-PRSBeamInformation,
   iE-Extensions ProtocolExtensionContainer { { SpatialDirectionInformation-ExtIEs } } OPTIONAL
}

SpatialDirectionInformation-ExtIEs F1AP-PROTOCOL-EXTENSION ::= {
   ...
}

SpatialRelationInfo ::= SEQUENCE {
   spatialRelationforResourceID SpatialRelationforResourceID,
   iE-Extensions ProtocolExtensionContainer { {SpatialRelationInfo-ExtIEs} } OPTIONAL
}

SpatialRelationInfo-ExtIEs F1AP-PROTOCOL-EXTENSION ::= {
   ...
}

SpatialRelationforResourceID ::= SEQUENCE (SIZE(1..maxnoofSpatialRelations)) OF SpatialRelationforResourceIDItem

SpatialRelationforResourceIDItem ::= SEQUENCE {
   referenceSignal ReferenceSignal,
   iE-Extensions ProtocolExtensionContainer { {SpatialRelationforResourceIDItem-ExtIEs} } OPTIONAL
}

SpatialRelationforResourceIDItem-ExtIEs F1AP-PROTOCOL-EXTENSION ::= {
   ...
}

SpatialRelationPerSRSResource ::= SEQUENCE {
   spatialRelationPerSRSResource-List SpatialRelationPerSRSResource-List,
   iE-Extensions ProtocolExtensionContainer { { SpatialRelationPerSRSResource-ExtIEs} } OPTIONAL,
   ...
}

SpatialRelationPerSRSResource-ExtIEs F1AP-PROTOCOL-EXTENSION ::= {
   ...
}

SpatialRelationPerSRSResource-List::= SEQUENCE(SIZE (1.. maxnoSRS-ResourcePerSet)) OF SpatialRelationPerSRSResourceItem

SpatialRelationPerSRSResourceItem ::= SEQUENCE {
   referenceSignal ReferenceSignal,
   iE-Extensions ProtocolExtensionContainer { { SpatialRelationPerSRSResourceItem-ExtIEs} } OPTIONAL,
   ...
}

SpatialRelationPerSRSResourceItem-ExtIEs F1AP-PROTOCOL-EXTENSION ::= {
   ...
}

SpatialRelationPos ::= CHOICE {
   sSBPos SSB,
   pRSInformationPos PRSInformationPos,
   choice-extension ProtocolIE-SingleContainer {{ SpatialInformationPos-ExtIEs }}
}

SpatialInformationPos-ExtIEs F1AP-PROTOCOL-IES ::= {
   ...
}

SpectrumSharingGroupID ::= INTEGER (1..maxCellineNB)

SRBID ::= INTEGER (0..3, ...)

SRBs-FailedToBeSetup-Item ::= SEQUENCE {
   sRBID SRBID ,
   cause Cause OPTIONAL,
   iE-Extensions ProtocolExtensionContainer { { SRBs-FailedToBeSetup-ItemExtIEs } } OPTIONAL,
   ...
}

SRBs-FailedToBeSetup-ItemExtIEs F1AP-PROTOCOL-EXTENSION ::= {
   ...
}

SRBs-FailedToBeSetupMod-Item ::= SEQUENCE {
   sRBID SRBID ,
   cause Cause OPTIONAL,
   iE-Extensions ProtocolExtensionContainer { { SRBs-FailedToBeSetupMod-ItemExtIEs } } OPTIONAL,
   ...
}

SRBs-FailedToBeSetupMod-ItemExtIEs F1AP-PROTOCOL-EXTENSION ::= {
   ...
}

SRBs-Modified-Item ::= SEQUENCE {
   sRBID SRBID,
   lCID LCID,
   iE-Extensions ProtocolExtensionContainer { { SRBs-Modified-ItemExtIEs } } OPTIONAL,
   ...
}

SRBs-Modified-ItemExtIEs F1AP-PROTOCOL-EXTENSION ::= {
   ...
}

SRBs-Required-ToBeReleased-Item ::= SEQUENCE {
   sRBID SRBID,
   iE-Extensions ProtocolExtensionContainer { { SRBs-Required-ToBeReleased-ItemExtIEs } } OPTIONAL,
   ...
}

SRBs-Required-ToBeReleased-ItemExtIEs F1AP-PROTOCOL-EXTENSION ::= {
   ...
}

SRBs-Setup-Item ::= SEQUENCE {
   sRBID SRBID,
   lCID LCID,
   iE-Extensions ProtocolExtensionContainer { { SRBs-Setup-ItemExtIEs } } OPTIONAL,
   ...
}

SRBs-Setup-ItemExtIEs F1AP-PROTOCOL-EXTENSION ::= {
   ...
}

SRBs-SetupMod-Item ::= SEQUENCE {
   sRBID SRBID,
   lCID LCID,
   iE-Extensions ProtocolExtensionContainer { { SRBs-SetupMod-ItemExtIEs } } OPTIONAL,
   ...
}

SRBs-SetupMod-ItemExtIEs F1AP-PROTOCOL-EXTENSION ::= {
   ...
}

SRBs-ToBeReleased-Item ::= SEQUENCE {
   sRBID SRBID,
   iE-Extensions ProtocolExtensionContainer { { SRBs-ToBeReleased-ItemExtIEs } } OPTIONAL,
   ...
}

SRBs-ToBeReleased-ItemExtIEs F1AP-PROTOCOL-EXTENSION ::= {
   ...
}

SRBs-ToBeSetup-Item ::= SEQUENCE {
   sRBID SRBID ,
   duplicationIndication DuplicationIndication OPTIONAL,
   iE-Extensions ProtocolExtensionContainer { { SRBs-ToBeSetup-ItemExtIEs } } OPTIONAL,
   ...
}

SRBs-ToBeSetup-ItemExtIEs F1AP-PROTOCOL-EXTENSION ::= {
   { ID id-AdditionalDuplicationIndication CRITICALITY ignore EXTENSION AdditionalDuplicationIndication PRESENCE optional },
   ...
}

SRBs-ToBeSetupMod-Item ::= SEQUENCE {
   sRBID SRBID,
   duplicationIndication DuplicationIndication OPTIONAL,
   iE-Extensions ProtocolExtensionContainer { { SRBs-ToBeSetupMod-ItemExtIEs } } OPTIONAL,
   ...
}

SRBs-ToBeSetupMod-ItemExtIEs F1AP-PROTOCOL-EXTENSION ::= {
   { ID id-AdditionalDuplicationIndication CRITICALITY ignore EXTENSION AdditionalDuplicationIndication PRESENCE optional },
   ...
}

SRSCarrier-List ::= SEQUENCE (SIZE(1.. maxnoSRS-Carriers)) OF SRSCarrier-List-Item

SRSCarrier-List-Item ::= SEQUENCE {
   pointA INTEGER (0..3279165),
   uplinkChannelBW-PerSCS-List UplinkChannelBW-PerSCS-List,
   activeULBWP ActiveULBWP,
   pci NRPCI OPTIONAL,
   iE-Extensions ProtocolExtensionContainer { { SRSCarrier-List-Item-ExtIEs } } OPTIONAL
}

SRSCarrier-List-Item-ExtIEs F1AP-PROTOCOL-EXTENSION ::= {
   ...
}

SRSConfig ::= SEQUENCE {
   sRSResource-List SRSResource-List OPTIONAL,
   posSRSResource-List PosSRSResource-List OPTIONAL,
   sRSResourceSet-List SRSResourceSet-List OPTIONAL,
   posSRSResourceSet-List PosSRSResourceSet-List OPTIONAL,
   iE-Extensions ProtocolExtensionContainer { { SRSConfig-ExtIEs } } OPTIONAL
}

SRSConfig-ExtIEs F1AP-PROTOCOL-EXTENSION ::= {
   ...
}

SRSConfiguration ::= SEQUENCE {
   sRSCarrier-List SRSCarrier-List,
   iE-Extensions ProtocolExtensionContainer { { SRSConfiguration-ExtIEs } } OPTIONAL
}

SRSConfiguration-ExtIEs F1AP-PROTOCOL-EXTENSION ::= {
   ...
}

SrsFrequency ::= INTEGER (0..3279165)

SRSPosResourceID ::= INTEGER (0..63)

SRSResource::= SEQUENCE {
   sRSResourceID SRSResourceID,
   nrofSRS-Ports ENUMERATED {port1, ports2, ports4},
   transmissionComb TransmissionComb,
   startPosition INTEGER (0..13),
   nrofSymbols ENUMERATED {n1, n2, n4},
   repetitionFactor ENUMERATED {n1, n2, n4},
   freqDomainPosition INTEGER (0..67),
   freqDomainShift INTEGER (0..268),
   c-SRS INTEGER (0..63),
   b-SRS INTEGER (0..3),
   b-hop INTEGER (0..3),
   groupOrSequenceHopping ENUMERATED { neither, groupHopping, sequenceHopping },
   resourceType ResourceType,
   sequenceId INTEGER (0..1023),
   iE-Extensions ProtocolExtensionContainer { { SRSResource-ExtIEs } } OPTIONAL
}

SRSResource-ExtIEs F1AP-PROTOCOL-EXTENSION ::= {
   ...
}

SRSResourceID ::= INTEGER (0..63)

SRSResourceID-List::= SEQUENCE (SIZE (1..maxnoSRS-ResourcePerSet)) OF SRSResourceID

SRSResource-List ::= SEQUENCE (SIZE (1..maxnoSRS-Resources)) OF SRSResource

SRSResourceSet::= SEQUENCE {
   sRSResourceSetID SRSResourceSetID,
   sRSResourceID-List SRSResourceID-List,
   resourceSetType ResourceSetType,
   iE-Extensions ProtocolExtensionContainer { { SRSResourceSet-ExtIEs } } OPTIONAL
}

SRSResourceSet-ExtIEs F1AP-PROTOCOL-EXTENSION ::= {
   ...
}

SRSResourceSetID ::= INTEGER (0..15, ...)

SRSResourceSetList ::= SEQUENCE (SIZE(1.. maxnoSRS-ResourceSets)) OF SRSResourceSetItem

SRSResourceSetItem ::= SEQUENCE {
   numSRSresourcesperset INTEGER (1..16, ...) OPTIONAL,
   periodicityList PeriodicityList OPTIONAL,
   spatialRelationInfo SpatialRelationInfo OPTIONAL,
   pathlossReferenceInfo PathlossReferenceInfo OPTIONAL,
   iE-Extensions ProtocolExtensionContainer { { SRSResourceSetItemExtIEs } } OPTIONAL
}

SRSResourceSetItemExtIEs F1AP-PROTOCOL-EXTENSION ::= {
   { ID id-SRSSpatialRelationPerSRSResource CRITICALITY ignore EXTENSION SpatialRelationPerSRSResource PRESENCE optional},
   ...
}

SRSResourceSet-List ::= SEQUENCE (SIZE (1..maxnoSRS-ResourceSets)) OF SRSResourceSet

SRSResourceTrigger ::= SEQUENCE {
   aperiodicSRSResourceTriggerList AperiodicSRSResourceTriggerList,
   iE-Extensions ProtocolExtensionContainer { {SRSResourceTrigger-ExtIEs} } OPTIONAL
}

SRSResourceTrigger-ExtIEs F1AP-PROTOCOL-EXTENSION ::= {
   ...
}

SSB ::= SEQUENCE {
   pCI-NR NRPCI,
   ssb-index SSB-Index OPTIONAL,
   iE-Extensions ProtocolExtensionContainer { {SSB-ExtIEs} } OPTIONAL
}

SSB-ExtIEs F1AP-PROTOCOL-EXTENSION ::= {
   ...
}

SSB-freqInfo ::= INTEGER (0..maxNRARFCN)

SSB-Index ::= INTEGER(0..63)

SSB-subcarrierSpacing ::= ENUMERATED {kHz15, kHz30, kHz120, kHz240, spare3, spare2, spare1, ...}

SSB-transmissionPeriodicity ::= ENUMERATED {sf10, sf20, sf40, sf80, sf160, sf320, sf640, ...}

SSB-transmissionTimingOffset ::= INTEGER (0..127, ...)

SSB-transmissionBitmap ::= CHOICE {
   shortBitmap BIT STRING (SIZE (4)),
   mediumBitmap BIT STRING (SIZE (8)),
   longBitmap BIT STRING (SIZE (64)),
   choice-extension ProtocolIE-SingleContainer { { SSB-transmisisonBitmap-ExtIEs} }
}

SSB-transmisisonBitmap-ExtIEs F1AP-PROTOCOL-IES ::= {
   ...
}

SSBAreaCapacityValueList ::= SEQUENCE (SIZE(1.. maxnoofSSBAreas)) OF SSBAreaCapacityValueItem

SSBAreaCapacityValueItem ::= SEQUENCE {
   sSBIndex INTEGER(0..63),
   sSBAreaCapacityValue INTEGER (0..100),
   iE-Extensions ProtocolExtensionContainer { { SSBAreaCapacityValueItem-ExtIEs} } OPTIONAL
}

SSBAreaCapacityValueItem-ExtIEs F1AP-PROTOCOL-EXTENSION ::= {
   ...
}

SSBAreaRadioResourceStatusList::= SEQUENCE (SIZE(1.. maxnoofSSBAreas)) OF SSBAreaRadioResourceStatusItem

SSBAreaRadioResourceStatusItem::= SEQUENCE {
   sSBIndex INTEGER(0..63),
   sSBAreaDLGBRPRBusage INTEGER (0..100),
   sSBAreaULGBRPRBusage INTEGER (0..100),
   sSBAreaDLnon-GBRPRBusage INTEGER (0..100),
   sSBAreaULnon-GBRPRBusage INTEGER (0..100),
   sSBAreaDLTotalPRBusage INTEGER (0..100),
   sSBAreaULTotalPRBusage INTEGER (0..100),
   dLschedulingPDCCHCCEusage INTEGER (0..100) OPTIONAL,
   uLschedulingPDCCHCCEusage INTEGER (0..100) OPTIONAL,
   iE-Extensions ProtocolExtensionContainer { { SSBAreaRadioResourceStatusItem-ExtIEs} } OPTIONAL
}

SSBAreaRadioResourceStatusItem-ExtIEs F1AP-PROTOCOL-EXTENSION ::= {
   ...
}

SSBInformation ::= SEQUENCE {
   sSBInformationList SSBInformationList,
   iE-Extensions ProtocolExtensionContainer { { SSBInformation-ExtIEs } } OPTIONAL
}

SSBInformation-ExtIEs F1AP-PROTOCOL-EXTENSION ::= {
   ...
}

SSBInformationList ::= SEQUENCE (SIZE(1.. maxnoofSSBs)) OF SSBInformationItem

SSBInformationItem ::= SEQUENCE {
   sSB-Configuration SSB-TF-Configuration,
   pCI-NR NRPCI,
   iE-Extensions ProtocolExtensionContainer { { SSBInformationItem-ExtIEs } } OPTIONAL
}

SSBInformationItem-ExtIEs F1AP-PROTOCOL-EXTENSION ::= {
   ...
}

SSB-PositionsInBurst ::= CHOICE {
   shortBitmap BIT STRING (SIZE (4)),
   mediumBitmap BIT STRING (SIZE (8)),
   longBitmap BIT STRING (SIZE (64)),
   choice-extension ProtocolIE-SingleContainer { {SSB-PositionsInBurst-ExtIEs} }
}

SSB-PositionsInBurst-ExtIEs F1AP-PROTOCOL-IES ::= {
   ...
}

SSB-TF-Configuration ::= SEQUENCE {
   sSB-frequency INTEGER (0..3279165),
   sSB-subcarrier-spacing ENUMERATED {kHz15, kHz30, kHz60, kHz120, kHz240, ...},
   sSB-Transmit-power INTEGER (-60..50),
   sSB-periodicity ENUMERATED {ms5, ms10, ms20, ms40, ms80, ms160, ...},
   sSB-half-frame-offset INTEGER(0..1),
   sSB-SFN-offset INTEGER(0..15),
   sSB-position-in-burst SSB-PositionsInBurst OPTIONAL,
   sFNInitialisationTime RelativeTime1900 OPTIONAL,
   iE-Extensions ProtocolExtensionContainer { { SSB-TF-Configuration-ExtIEs} } OPTIONAL
}

SSB-TF-Configuration-ExtIEs F1AP-PROTOCOL-EXTENSION ::= {
   ...
}

SSBToReportList ::= SEQUENCE (SIZE(1.. maxnoofSSBAreas)) OF SSBToReportItem

SSBToReportItem ::= SEQUENCE {
   sSBIndex INTEGER(0..63),
   iE-Extensions ProtocolExtensionContainer { { SSBToReportItem-ExtIEs} } OPTIONAL
}

SSBToReportItem-ExtIEs F1AP-PROTOCOL-EXTENSION ::= {
   ...
}

SUL-Information ::= SEQUENCE {
   sUL-NRARFCN INTEGER (0..maxNRARFCN),
   sUL-transmission-Bandwidth Transmission-Bandwidth,
   iE-Extensions ProtocolExtensionContainer { { SUL-InformationExtIEs} } OPTIONAL,
   ...
}

SUL-InformationExtIEs F1AP-PROTOCOL-EXTENSION ::= {
   { ID id-CarrierList CRITICALITY ignore EXTENSION NRCarrierList PRESENCE optional }|
   { ID id-FrequencyShift7p5khz CRITICALITY ignore EXTENSION FrequencyShift7p5khz PRESENCE optional },
   ...
}

SubcarrierSpacing ::= ENUMERATED { kHz15, kHz30, kHz60, kHz120, kHz240, spare3, spare2, spare1, ...}

SubscriberProfileIDforRFP ::= INTEGER (1..256, ...)

SULAccessIndication ::= ENUMERATED {true,...}

SupportedSULFreqBandItem ::= SEQUENCE {
   freqBandIndicatorNr INTEGER (1..1024,...),
   iE-Extensions ProtocolExtensionContainer { { SupportedSULFreqBandItem-ExtIEs} } OPTIONAL,
   ...
}

SupportedSULFreqBandItem-ExtIEs F1AP-PROTOCOL-EXTENSION ::= {
   ...
}

SymbolAllocInSlot ::= CHOICE {
   all-DL NULL,
   all-UL NULL,
   both-DL-and-UL NumDLULSymbols,
   choice-extension ProtocolIE-SingleContainer { { SymbolAllocInSlot-ExtIEs } }
}

SymbolAllocInSlot-ExtIEs F1AP-PROTOCOL-IES ::= {
   ...
}

SystemFrameNumber ::= INTEGER (0..1023)

SystemInformationAreaID ::=BIT STRING (SIZE (24))

-- T

FiveGS-TAC ::= OCTET STRING (SIZE(3))

Configured-EPS-TAC ::= OCTET STRING (SIZE(2))

TargetCellList ::= SEQUENCE (SIZE(1..maxnoofCHOcells)) OF TargetCellList-Item

TargetCellList-Item ::= SEQUENCE {
   target-cell NRCGI,
   iE-Extensions ProtocolExtensionContainer { { TargetCellList-Item-ExtIEs} } OPTIONAL
}

TargetCellList-Item-ExtIEs F1AP-PROTOCOL-EXTENSION ::= {
   ...
}

TDD-Info ::= SEQUENCE {
   nRFreqInfo NRFreqInfo,
   transmission-Bandwidth Transmission-Bandwidth,
   iE-Extensions ProtocolExtensionContainer { {TDD-Info-ExtIEs} } OPTIONAL,
   ...
}

TDD-Info-ExtIEs F1AP-PROTOCOL-EXTENSION ::= {
   {ID id-IntendedTDD-DL-ULConfig CRITICALITY ignore EXTENSION IntendedTDD-DL-ULConfig PRESENCE optional}|
   {ID id-TDD-UL-DLConfigCommonNR CRITICALITY ignore EXTENSION TDD-UL-DLConfigCommonNR PRESENCE optional }|
   {ID id-CarrierList CRITICALITY ignore EXTENSION NRCarrierList PRESENCE optional },
   ...
}

TDD-UL-DLConfigCommonNR ::= OCTET STRING

TimeReferenceInformation ::= SEQUENCE {
   referenceTime ReferenceTime,
   referenceSFN ReferenceSFN,
   uncertainty Uncertainty,
   timeInformationType TimeInformationType,
   iE-Extensions ProtocolExtensionContainer { {TimeReferenceInformation-ExtIEs} } OPTIONAL
}

TimeReferenceInformation-ExtIEs F1AP-PROTOCOL-EXTENSION ::= {
   ...
}

TimeInformationType ::= ENUMERATED {localClock}

TimeStamp ::= SEQUENCE {
   systemFrameNumber SystemFrameNumber,
   slotIndex TimeStampSlotIndex,
   measurementTime RelativeTime1900 OPTIONAL,
   iE-Extension ProtocolExtensionContainer { { TimeStamp-ExtIEs} } OPTIONAL
}

TimeStamp-ExtIEs F1AP-PROTOCOL-EXTENSION ::= {
   ...
}

TimeStampSlotIndex ::= CHOICE {
   sCS-15 INTEGER(0..9),
   sCS-30 INTEGER(0..19),
   sCS-60 INTEGER(0..39),
   sCS-120 INTEGER(0..79),
   choice-extension ProtocolIE-SingleContainer { { TimeStampSlotIndex-ExtIEs} }
}

TimeStampSlotIndex-ExtIEs F1AP-PROTOCOL-IES ::= {
   ...
}

TimeToWait ::= ENUMERATED {v1s, v2s, v5s, v10s, v20s, v60s, ...}

TimingMeasurementQuality ::= SEQUENCE {
   measurementQuality INTEGER(0..31),
   resolution ENUMERATED{m0dot1, m1, m10, m30, ...},
   iE-Extensions ProtocolExtensionContainer { { TimingMeasurementQuality-ExtIEs} } OPTIONAL
}

TimingMeasurementQuality-ExtIEs F1AP-PROTOCOL-EXTENSION ::= {
   ...
}

TNLAssociationUsage ::= ENUMERATED {
   ue,
   non-ue,
   both,
   ...
}

TNLCapacityIndicator::= SEQUENCE {
   dLTNLOfferedCapacity INTEGER (1.. 16777216,...),
   dLTNLAvailableCapacity INTEGER (0.. 100,...),
   uLTNLOfferedCapacity INTEGER (1.. 16777216,...),
   uLTNLAvailableCapacity INTEGER (0.. 100,...),
   iE-Extensions ProtocolExtensionContainer { { TNLCapacityIndicator-ExtIEs} } OPTIONAL
}

TNLCapacityIndicator-ExtIEs F1AP-PROTOCOL-EXTENSION ::= {
   ...
}

TraceActivation ::= SEQUENCE {
   traceID TraceID,
   interfacesToTrace InterfacesToTrace,
   traceDepth TraceDepth,
   traceCollectionEntityIPAddress TransportLayerAddress,
   iE-Extensions ProtocolExtensionContainer { {TraceActivation-ExtIEs} } OPTIONAL
}

TraceActivation-ExtIEs F1AP-PROTOCOL-EXTENSION ::= {
   {ID id-mdtConfiguration CRITICALITY ignore EXTENSION MDTConfiguration PRESENCE optional}|
   {ID id-TraceCollectionEntityURI CRITICALITY ignore EXTENSION URI-address PRESENCE optional },
   ...
}

TraceDepth ::= ENUMERATED {
   minimum,
   medium,
   maximum,
   minimumWithoutVendorSpecificExtension,
   mediumWithoutVendorSpecificExtension,
   maximumWithoutVendorSpecificExtension,
   ...
}

TraceID ::= OCTET STRING (SIZE(8))

TrafficMappingInfo ::= CHOICE {
   iPtolayer2TrafficMappingInfo IPtolayer2TrafficMappingInfo,
   bAPlayerBHRLCchannelMappingInfo BAPlayerBHRLCchannelMappingInfo,
   choice-extension ProtocolIE-SingleContainer { { TrafficMappingInfo-ExtIEs} }
}

TrafficMappingInfo-ExtIEs F1AP-PROTOCOL-IES ::= {
   ...
}

TransportLayerAddress ::= BIT STRING (SIZE(1..160, ...))

TransactionID ::= INTEGER (0..255, ...)

Transmission-Bandwidth ::= SEQUENCE {
   nRSCS NRSCS,
   nRNRB NRNRB,
   iE-Extensions ProtocolExtensionContainer { { Transmission-Bandwidth-ExtIEs} } OPTIONAL,
   ...
}

Transmission-Bandwidth-ExtIEs F1AP-PROTOCOL-EXTENSION ::= {
   ...
}

TransmissionComb ::= CHOICE {
   n2 SEQUENCE {
      combOffset-n2 INTEGER (0..1),
      cyclicShift-n2 INTEGER (0..7)
      },
   n4 SEQUENCE {
      combOffset-n4 INTEGER (0..3),
      cyclicShift-n4 INTEGER (0..11)
      },
   choice-extension ProtocolIE-SingleContainer { { TransmissionComb-ExtIEs} }
}
TransmissionComb-ExtIEs F1AP-PROTOCOL-IES ::= {
   ...
}

TransmissionCombPos ::= CHOICE {
   n2 SEQUENCE {
      combOffset-n2 INTEGER (0..1),
      cyclicShift-n2 INTEGER (0..7)
      },
   n4 SEQUENCE {
      combOffset-n4 INTEGER (0..3),
      cyclicShift-n4 INTEGER (0..11)
      },
   n8 SEQUENCE {
      combOffset-n8 INTEGER (0..7),
      cyclicShift-n8 INTEGER (0..5)
      },

   choice-extension ProtocolIE-SingleContainer { { TransmissionCombPos-ExtIEs} }
}
TransmissionCombPos-ExtIEs F1AP-PROTOCOL-IES ::= {
   ...
}

TransmissionStopIndicator ::= ENUMERATED {true, ... }

Transport-UP-Layer-Address-Info-To-Add-List ::= SEQUENCE (SIZE(1.. maxnoofTLAs)) OF Transport-UP-Layer-Address-Info-To-Add-Item

Transport-UP-Layer-Address-Info-To-Add-Item ::= SEQUENCE {
   iP-SecTransportLayerAddress TransportLayerAddress,
   gTPTransportLayerAddressToAdd GTPTLAs OPTIONAL,
   iE-Extensions ProtocolExtensionContainer { { Transport-UP-Layer-Address-Info-To-Add-ItemExtIEs } } OPTIONAL
}

Transport-UP-Layer-Address-Info-To-Add-ItemExtIEs F1AP-PROTOCOL-EXTENSION ::= {
   ...
}

Transport-UP-Layer-Address-Info-To-Remove-List ::= SEQUENCE (SIZE(1.. maxnoofTLAs)) OF Transport-UP-Layer-Address-Info-To-Remove-Item

Transport-UP-Layer-Address-Info-To-Remove-Item ::= SEQUENCE {
   iP-SecTransportLayerAddress TransportLayerAddress,
   gTPTransportLayerAddressToRemove GTPTLAs OPTIONAL,
   iE-Extensions ProtocolExtensionContainer { { Transport-UP-Layer-Address-Info-To-Remove-ItemExtIEs } } OPTIONAL
}

Transport-UP-Layer-Address-Info-To-Remove-ItemExtIEs F1AP-PROTOCOL-EXTENSION ::= {
   ...
}

TransmissionActionIndicator ::= ENUMERATED {stop, ..., restart }

TRPID ::= INTEGER (0.. maxnoofTRPs, ...)

TRPInformation ::= SEQUENCE {
   tRPID TRPID,
   tRPInformationTypeResponseList TRPInformationTypeResponseList,
   iE-Extensions ProtocolExtensionContainer { { TRPInformation-ExtIEs } } OPTIONAL
}

TRPInformation-ExtIEs F1AP-PROTOCOL-EXTENSION ::= {
   ...
}

TRPInformationItem ::= SEQUENCE {
   tRPInformation TRPInformation,
   iE-Extensions ProtocolExtensionContainer { { TRPInformationItem-ExtIEs } } OPTIONAL
}

TRPInformationItem-ExtIEs F1AP-PROTOCOL-EXTENSION ::= {
   ...
}

TRPInformationTypeItem ::= ENUMERATED {
   nrPCI,
   nG-RAN-CGI,
   arfcn,
   pRSConfig,
   sSBConfig,
   sFNInitTime,
   spatialDirectInfo,
   geoCoord,
   ...,
   trp-type
}

TRPInformationTypeResponseList ::= SEQUENCE (SIZE(1.. maxnoofTRPInfoTypes)) OF TRPInformationTypeResponseItem

TRPInformationTypeResponseItem ::= CHOICE {
   pCI-NR NRPCI,
   nG-RAN-CGI NRCGI,
   nRARFCN INTEGER (0..maxNRARFCN),
   pRSConfiguration PRSConfiguration,
   sSBinformation SSBInformation,
   sFNInitialisationTime RelativeTime1900,
   spatialDirectionInformation SpatialDirectionInformation,
   geographicalCoordinates GeographicalCoordinates,
   choice-extension ProtocolIE-SingleContainer { { TRPInformationTypeResponseItem-ExtIEs} }
}

TRPInformationTypeResponseItem-ExtIEs F1AP-PROTOCOL-IES ::= {
   { ID id-TRPType CRITICALITY reject TYPE TRPType PRESENCE mandatory },
   ...
}

TRPList ::= SEQUENCE (SIZE(1.. maxnoofTRPs)) OF TRPListItem

TRPListItem ::= SEQUENCE {
   tRPID TRPID,
   iE-Extensions ProtocolExtensionContainer { { TRPListItem-ExtIEs } } OPTIONAL
}

TRPListItem-ExtIEs F1AP-PROTOCOL-EXTENSION ::= {
   ...
}

TRPMeasurementQuality ::= SEQUENCE {
   tRPmeasurementQuality-Item TRPMeasurementQuality-Item,
   iE-Extensions ProtocolExtensionContainer { {TRPMeasurementQuality-ExtIEs} } OPTIONAL
}

TRPMeasurementQuality-ExtIEs F1AP-PROTOCOL-EXTENSION ::= {
   ...
}

TRPMeasurementQuality-Item ::= CHOICE {
   timingMeasurementQuality TimingMeasurementQuality,
   angleMeasurementQuality AngleMeasurementQuality,
   choice-extension ProtocolIE-SingleContainer { { TRPMeasurementQuality-Item-ExtIEs } }
}

TRPMeasurementQuality-Item-ExtIEs F1AP-PROTOCOL-IES ::= {
   ...
}

TRP-MeasurementRequestList ::= SEQUENCE (SIZE (1..maxNoOfMeasTRPs)) OF TRP-MeasurementRequestItem

TRP-MeasurementRequestItem ::= SEQUENCE {
   tRPID TRPID,
   search-window-information Search-window-information OPTIONAL,
   iE-extensions ProtocolExtensionContainer { { TRP-MeasurementRequestItem-ExtIEs } } OPTIONAL
}

TRP-MeasurementRequestItem-ExtIEs F1AP-PROTOCOL-EXTENSION ::= {
   { ID id-NRCGI CRITICALITY ignore EXTENSION NRCGI PRESENCE optional },
   ...
}

TRPPositionDefinitionType ::= CHOICE {
   direct TRPPositionDirect,
   referenced TRPPositionReferenced,
   choice-extension ProtocolIE-SingleContainer { { TRPPositionDefinitionType-ExtIEs } }
}

TRPPositionDefinitionType-ExtIEs F1AP-PROTOCOL-IES ::= {
   ...
}

TRPPositionDirect ::= SEQUENCE {
   accuracy TRPPositionDirectAccuracy,
   iE-extensions ProtocolExtensionContainer { { TRPPositionDirect-ExtIEs } } OPTIONAL
}

TRPPositionDirect-ExtIEs F1AP-PROTOCOL-EXTENSION ::= {
   ...
}

TRPPositionDirectAccuracy ::= CHOICE {
   tRPPosition AccessPointPosition,
   tRPHAposition NGRANHighAccuracyAccessPointPosition,
   choice-extension ProtocolIE-SingleContainer { { TRPPositionDirectAccuracy-ExtIEs } }
}

TRPPositionDirectAccuracy-ExtIEs F1AP-PROTOCOL-IES ::= {
   ...
}

TRPPositionReferenced ::= SEQUENCE {
   referencePoint ReferencePoint,
   referencePointType TRPReferencePointType,
   iE-extensions ProtocolExtensionContainer { { TRPPositionReferenced-ExtIEs } } OPTIONAL
}

TRPPositionReferenced-ExtIEs F1AP-PROTOCOL-EXTENSION ::= {
   ...
}

TRPReferencePointType ::= CHOICE {
   tRPPositionRelativeGeodetic RelativeGeodeticLocation,
   tRPPositionRelativeCartesian RelativeCartesianLocation,
   choice-extension ProtocolIE-SingleContainer { { TRPReferencePointType-ExtIEs } }
}

TRPReferencePointType-ExtIEs F1AP-PROTOCOL-IES ::= {
   ...
}

TypeOfError ::= ENUMERATED {
   not-understood,
   missing,
   ...
}

Transport-Layer-Address-Info ::= SEQUENCE {
   transport-UP-Layer-Address-Info-To-Add-List Transport-UP-Layer-Address-Info-To-Add-List OPTIONAL,
   transport-UP-Layer-Address-Info-To-Remove-List Transport-UP-Layer-Address-Info-To-Remove-List OPTIONAL,
   iE-Extensions ProtocolExtensionContainer { { Transport-Layer-Address-Info-ExtIEs } } OPTIONAL
}

Transport-Layer-Address-Info-ExtIEs F1AP-PROTOCOL-EXTENSION ::= {
   ...
}

TRPType ::= ENUMERATED {
   prsOnlyTP,
   srsOnlyRP,
   tp,
   rp,
   trp,
   ...
}

TSCAssistanceInformation ::= SEQUENCE {
   periodicity Periodicity,
   burstArrivalTime BurstArrivalTime OPTIONAL,
   iE-Extensions ProtocolExtensionContainer { {TSCAssistanceInformation-ExtIEs} } OPTIONAL,
   ...
}

TSCAssistanceInformation-ExtIEs F1AP-PROTOCOL-EXTENSION ::= {
   ...
}

TSCTrafficCharacteristics ::= SEQUENCE {
   tSCAssistanceInformationDL TSCAssistanceInformation OPTIONAL,
   tSCAssistanceInformationUL TSCAssistanceInformation OPTIONAL,
   iE-Extensions ProtocolExtensionContainer { {TSCTrafficCharacteristics-ExtIEs} } OPTIONAL,
   ...
}

TSCTrafficCharacteristics-ExtIEs F1AP-PROTOCOL-EXTENSION ::= {
   ...
}

-- U
UAC-Assistance-Info ::= SEQUENCE {
   uACPLMN-List UACPLMN-List,
   iE-Extensions ProtocolExtensionContainer { { UAC-Assistance-InfoExtIEs} } OPTIONAL
}

UAC-Assistance-InfoExtIEs F1AP-PROTOCOL-EXTENSION ::= {
   ...
}

UACPLMN-List ::= SEQUENCE (SIZE(1..maxnoofUACPLMNs)) OF UACPLMN-Item

UACPLMN-Item::= SEQUENCE {
   pLMNIdentity PLMN-Identity,
   uACType-List UACType-List, iE-Extensions ProtocolExtensionContainer { { UACPLMN-Item-ExtIEs} } OPTIONAL
}

UACPLMN-Item-ExtIEs F1AP-PROTOCOL-EXTENSION ::= {
   { ID id-NID CRITICALITY ignore EXTENSION NID PRESENCE optional },
   ...
}

UACType-List ::= SEQUENCE (SIZE(1..maxnoofUACperPLMN)) OF UACType-Item

UACType-Item::= SEQUENCE {
   uACReductionIndication UACReductionIndication,
   uACCategoryType UACCategoryType,
   iE-Extensions ProtocolExtensionContainer { { UACType-Item-ExtIEs } } OPTIONAL
}

UACType-Item-ExtIEs F1AP-PROTOCOL-EXTENSION ::= {
   ...
}

UACCategoryType ::= CHOICE {
   uACstandardized UACAction,
   uACOperatorDefined UACOperatorDefined,
   choice-extension ProtocolIE-SingleContainer { { UACCategoryType-ExtIEs } }
}

UACCategoryType-ExtIEs F1AP-PROTOCOL-IES ::= {
   ...
}

UACOperatorDefined ::= SEQUENCE {
   accessCategory INTEGER (32..63,...),
   accessIdentity BIT STRING (SIZE(7)),
   iE-Extensions ProtocolExtensionContainer { { UACOperatorDefined-ExtIEs} } OPTIONAL
}

UACOperatorDefined-ExtIEs F1AP-PROTOCOL-EXTENSION ::= {
   ...
}

UACAction ::= ENUMERATED {
   reject-non-emergency-mo-dt,
   reject-rrc-cr-signalling,
   permit-emergency-sessions-and-mobile-terminated-services-only,
   permit-high-priority-sessions-and-mobile-terminated-services-only,
   ...
}

UACReductionIndication ::= INTEGER (0..100)

UE-associatedLogicalF1-ConnectionItem ::= SEQUENCE {
   gNB-CU-UE-F1AP-ID GNB-CU-UE-F1AP-ID OPTIONAL,
   gNB-DU-UE-F1AP-ID GNB-DU-UE-F1AP-ID OPTIONAL,
   iE-Extensions ProtocolExtensionContainer { { UE-associatedLogicalF1-ConnectionItemExtIEs} } OPTIONAL,
   ...
}

UEAssistanceInformation ::= OCTET STRING

UEAssistanceInformationEUTRA ::= OCTET STRING

UE-associatedLogicalF1-ConnectionItemExtIEs F1AP-PROTOCOL-EXTENSION ::= {
   ...
}

UE-CapabilityRAT-ContainerList::= OCTET STRING

UEContextNotRetrievable ::= ENUMERATED {true, ...}

UEIdentityIndexValue ::= CHOICE {
   indexLength10 BIT STRING (SIZE (10)),
   choice-extension ProtocolIE-SingleContainer { {UEIdentityIndexValueChoice-ExtIEs} }
}

UEIdentityIndexValueChoice-ExtIEs F1AP-PROTOCOL-IES ::= {
   ...
}

UL-AoA ::= SEQUENCE {
   azimuthAoA INTEGER (0..3599),
   zenithAoA INTEGER (0..1799) OPTIONAL,
   lCS-to-GCS-TranslationAoA LCS-to-GCS-TranslationAoA OPTIONAL,
   iE-extensions ProtocolExtensionContainer { { UL-AoA-ExtIEs } }
}

UL-AoA-ExtIEs F1AP-PROTOCOL-EXTENSION ::= {
   ...
}

UL-BH-Non-UP-Traffic-Mapping ::= SEQUENCE {
   uL-BH-Non-UP-Traffic-Mapping-List UL-BH-Non-UP-Traffic-Mapping-List,
   iE-Extensions ProtocolExtensionContainer { { UL-BH-Non-UP-Traffic-Mapping-ExtIEs } } OPTIONAL
}

UL-BH-Non-UP-Traffic-Mapping-ExtIEs F1AP-PROTOCOL-EXTENSION ::= {
   ...
}

UL-BH-Non-UP-Traffic-Mapping-List ::= SEQUENCE (SIZE(1..maxnoofNonUPTrafficMappings)) OF UL-BH-Non-UP-Traffic-Mapping-Item

UL-BH-Non-UP-Traffic-Mapping-Item ::= SEQUENCE {
   nonUPTrafficType NonUPTrafficType,
   bHInfo BHInfo,
   iE-Extensions ProtocolExtensionContainer { { UL-BH-Non-UP-Traffic-Mapping-ItemExtIEs } } OPTIONAL
}

UL-BH-Non-UP-Traffic-Mapping-ItemExtIEs F1AP-PROTOCOL-EXTENSION ::= {
   ...
}

ULConfiguration ::= SEQUENCE {
   uLUEConfiguration ULUEConfiguration,
   iE-Extensions ProtocolExtensionContainer { { ULConfigurationExtIEs } } OPTIONAL,
   ...
}
ULConfigurationExtIEs F1AP-PROTOCOL-EXTENSION ::= {
   ...
}

UL-RTOA-Measurement ::= SEQUENCE {
   uL-RTOA-MeasurementItem UL-RTOA-MeasurementItem,
   additionalPath-List AdditionalPath-List OPTIONAL,
   iE-Extensions ProtocolExtensionContainer { { UL-RTOA-Measurement-ExtIEs } } OPTIONAL
}

UL-RTOA-Measurement-ExtIEs F1AP-PROTOCOL-EXTENSION ::= {
   ...
}

UL-RTOA-MeasurementItem ::= CHOICE {
   k0 INTEGER (0..1970049),
   k1 INTEGER (0..985025),
   k2 INTEGER (0..492513),
   k3 INTEGER (0..246257),
   k4 INTEGER (0..123129),
   k5 INTEGER (0..61565),
   choice-extension ProtocolIE-SingleContainer { { UL-RTOA-MeasurementItem-ExtIEs } }
}

UL-RTOA-MeasurementItem-ExtIEs F1AP-PROTOCOL-IES ::= {
   ...
}

UL-SRS-RSRP ::= INTEGER (0..126)

ULUEConfiguration ::= ENUMERATED {no-data, shared, only, ...}

UL-UP-TNL-Information-to-Update-List-Item ::= SEQUENCE {
   uLUPTNLInformation UPTransportLayerInformation,
   newULUPTNLInformation UPTransportLayerInformation OPTIONAL,
   bHInfo BHInfo,
   iE-Extensions ProtocolExtensionContainer { { UL-UP-TNL-Information-to-Update-List-ItemExtIEs } } OPTIONAL,
   ...
}

UL-UP-TNL-Information-to-Update-List-ItemExtIEs F1AP-PROTOCOL-EXTENSION ::= {
   ...
}

UL-UP-TNL-Address-to-Update-List-Item ::= SEQUENCE {
   oldIPAdress TransportLayerAddress,
   newIPAdress TransportLayerAddress,
   iE-Extensions ProtocolExtensionContainer { { UL-UP-TNL-Address-to-Update-List-ItemExtIEs } } OPTIONAL,
   ...
}

UL-UP-TNL-Address-to-Update-List-ItemExtIEs F1AP-PROTOCOL-EXTENSION ::= {
   ...
}

ULUPTNLInformation-ToBeSetup-List ::= SEQUENCE (SIZE(1..maxnoofULUPTNLInformation)) OF ULUPTNLInformation-ToBeSetup-Item

ULUPTNLInformation-ToBeSetup-Item ::=SEQUENCE {
   uLUPTNLInformation UPTransportLayerInformation,
   iE-Extensions ProtocolExtensionContainer { { ULUPTNLInformation-ToBeSetup-ItemExtIEs } } OPTIONAL,
   ...
}

ULUPTNLInformation-ToBeSetup-ItemExtIEs F1AP-PROTOCOL-EXTENSION ::= {
   { ID id-BHInfo CRITICALITY ignore EXTENSION BHInfo PRESENCE optional },
   ...
}

Uncertainty ::= INTEGER (0..32767, ...)

UplinkChannelBW-PerSCS-List ::= SEQUENCE (SIZE (1..maxnoSCSs)) OF SCS-SpecificCarrier

UplinkTxDirectCurrentListInformation ::= OCTET STRING

UPTransportLayerInformation ::= CHOICE {
   gTPTunnel GTPTunnel,
   choice-extension ProtocolIE-SingleContainer { { UPTransportLayerInformation-ExtIEs} }
}

UPTransportLayerInformation-ExtIEs F1AP-PROTOCOL-IES ::= {
   ...
}

URI-address ::= VisibleString

-- V

VictimgNBSetID ::= SEQUENCE {
   victimgNBSetID GNBSetID,
   iE-Extensions ProtocolExtensionContainer { { VictimgNBSetID-ExtIEs } } OPTIONAL
}

VictimgNBSetID-ExtIEs F1AP-PROTOCOL-EXTENSION ::= {
   ...
}

VehicleUE ::= ENUMERATED {
   authorized,
   not-authorized,
   ...
}

PedestrianUE ::= ENUMERATED {
   authorized,
   not-authorized,
   ...
}

-- W

-- X

-- Y

-- Z

END
-- ASN1STOP

-- ASN1START
-- **************************************************************
--
-- Common definitions
--
-- **************************************************************

F1AP-CommonDataTypes {
   itu-t (0) identified-organization (4) etsi (0) mobileDomain (0)
ngran-access (22) modules (3) f1ap (3) version1 (1) f1ap-CommonDataTypes (3) }

DEFINITIONS AUTOMATIC TAGS ::=

BEGIN

Criticality ::= ENUMERATED { reject, ignore, notify }

Presence ::= ENUMERATED { optional, conditional, mandatory }

PrivateIE-ID ::= CHOICE {
   local INTEGER (0..65535),
   global OBJECT IDENTIFIER
}

ProcedureCode ::= INTEGER (0..255)

ProtocolExtensionID ::= INTEGER (0..65535)

ProtocolIE-ID ::= INTEGER (0..65535)

TriggeringMessage ::= ENUMERATED { initiating-message, successful-outcome, unsuccessful-outcome }

END
-- ASN1STOP

-- ASN1START
-- **************************************************************
--
-- Constant definitions
--
-- **************************************************************

F1AP-Constants {
   itu-t (0) identified-organization (4) etsi (0) mobileDomain (0)
ngran-access (22) modules (3) f1ap (3) version1 (1) f1ap-Constants (4) }

DEFINITIONS AUTOMATIC TAGS ::=

BEGIN

-- **************************************************************
--
-- IE parameter types from other modules.
--
-- **************************************************************

IMPORTS
ProcedureCode,
ProtocolIE-ID

FROM F1AP-CommonDataTypes;

-- **************************************************************
--
-- Elementary Procedures
--
-- **************************************************************

id-Reset ProcedureCode ::= 0
id-F1Setup ProcedureCode ::= 1
id-ErrorIndication ProcedureCode ::= 2
id-gNBDUConfigurationUpdate ProcedureCode ::= 3
id-gNBCUConfigurationUpdate ProcedureCode ::= 4
id-UEContextSetup ProcedureCode ::= 5
id-UEContextRelease ProcedureCode ::= 6
id-UEContextModification ProcedureCode ::= 7
id-UEContextModificationRequired ProcedureCode ::= 8
id-UEMobilityCommand ProcedureCode ::= 9
id-UEContextReleaseRequest ProcedureCode ::= 10
id-InitialULRRCMessageTransfer ProcedureCode ::= 11
id-DLRRCMessageTransfer ProcedureCode ::= 12
id-ULRRCMessageTransfer ProcedureCode ::= 13
id-privateMessage ProcedureCode ::= 14
id-UEInactivityNotification ProcedureCode ::= 15
id-GNBDUResourceCoordination ProcedureCode ::= 16
id-SystemInformationDeliveryCommand ProcedureCode ::= 17
id-Paging ProcedureCode ::= 18
id-Notify ProcedureCode ::= 19
id-WriteReplaceWarning ProcedureCode ::= 20
id-PWSCancel ProcedureCode ::= 21
id-PWSRestartIndication ProcedureCode ::= 22
id-PWSFailureIndication ProcedureCode ::= 23
id-GNBDUStatusIndication ProcedureCode ::= 24
id-RRCDeliveryReport ProcedureCode ::= 25
id-F1Removal ProcedureCode ::= 26
id-NetworkAccessRateReduction ProcedureCode ::= 27
id-TraceStart ProcedureCode ::= 28
id-DeactivateTrace ProcedureCode ::= 29
id-DUCURadioInformationTransfer ProcedureCode ::= 30
id-CUDURadioInformationTransfer ProcedureCode ::= 31
id-BAPMappingConfiguration ProcedureCode ::= 32
id-GNBDUResourceConfiguration ProcedureCode ::= 33
id-IABTNLAddressAllocation ProcedureCode ::= 34
id-IABUPConfigurationUpdate ProcedureCode ::= 35
id-resourceStatusReportingInitiation ProcedureCode ::= 36
id-resourceStatusReporting ProcedureCode ::= 37
id-accessAndMobilityIndication ProcedureCode ::= 38
id-accessSuccess ProcedureCode ::= 39
id-cellTrafficTrace ProcedureCode ::= 40
id-PositioningMeasurementExchange ProcedureCode ::= 41
id-PositioningAssistanceInformationControl ProcedureCode ::= 42
id-PositioningAssistanceInformationFeedback ProcedureCode ::= 43
id-PositioningMeasurementReport ProcedureCode ::= 44
id-PositioningMeasurementAbort ProcedureCode ::= 45
id-PositioningMeasurementFailureIndication ProcedureCode ::= 46
id-PositioningMeasurementUpdate ProcedureCode ::= 47
id-TRPInformationExchange ProcedureCode ::= 48
id-PositioningInformationExchange ProcedureCode ::= 49
id-PositioningActivation ProcedureCode ::= 50
id-PositioningDeactivation ProcedureCode ::= 51
id-E-CIDMeasurementInitiation ProcedureCode ::= 52
id-E-CIDMeasurementFailureIndication ProcedureCode ::= 53
id-E-CIDMeasurementReport ProcedureCode ::= 54
id-E-CIDMeasurementTermination ProcedureCode ::= 55
id-PositioningInformationUpdate ProcedureCode ::= 56
id-ReferenceTimeInformationReport ProcedureCode ::= 57
id-ReferenceTimeInformationReportingControl ProcedureCode ::= 58

-- **************************************************************
--
-- Extension constants
--
-- **************************************************************

maxPrivateIEs INTEGER ::= 65535
maxProtocolExtensions INTEGER ::= 65535
maxProtocolIEs INTEGER ::= 65535
-- **************************************************************
--
-- Lists
--
-- **************************************************************

maxNRARFCN INTEGER ::= 3279165
maxnoofErrors INTEGER ::= 256
maxnoofIndividualF1ConnectionsToReset INTEGER ::= 65536
maxCellingNBDU INTEGER ::= 512
maxnoofSCells INTEGER ::= 32
maxnoofSRBs INTEGER ::= 8
maxnoofDRBs INTEGER ::= 64
maxnoofULUPTNLInformation INTEGER ::= 2
maxnoofDLUPTNLInformation INTEGER ::= 2
maxnoofBPLMNs INTEGER ::= 6
maxnoofCandidateSpCells INTEGER ::= 64
maxnoofPotentialSpCells INTEGER ::= 64
maxnoofNrCellBands INTEGER ::= 32
maxnoofSIBTypes INTEGER ::= 32
maxnoofSITypes INTEGER ::= 32
maxnoofPagingCells INTEGER ::= 512
maxnoofTNLAssociations INTEGER ::= 32
maxnoofQoSFlows INTEGER ::= 64
maxnoofSliceItems INTEGER ::= 1024
maxCellineNB INTEGER ::= 256
maxnoofExtendedBPLMNs INTEGER ::= 6
maxnoofUEIDs INTEGER ::= 65536
maxnoofBPLMNsNR INTEGER ::= 12
maxnoofUACPLMNs INTEGER ::= 12
maxnoofUACperPLMN INTEGER ::= 64
maxnoofAdditionalSIBs INTEGER ::= 63
maxnoofslots INTEGER ::= 5120
maxnoofTLAs INTEGER ::= 16
maxnoofGTPTLAs INTEGER ::= 16
maxnoofBHRLCChannels INTEGER ::= 65536
maxnoofRoutingEntries INTEGER ::= 1024
maxnoofIABSTCInfo INTEGER ::= 45
maxnoofSymbols INTEGER ::= 14
maxnoofServingCells INTEGER ::= 32
maxnoofDUFSlots INTEGER ::= 320
maxnoofHSNASlots INTEGER ::= 5120
maxnoofServedCellsIAB INTEGER ::= 512
maxnoofChildIABNodes INTEGER ::= 1024
maxnoofNonUPTrafficMappings INTEGER ::= 32
maxnoofTLAsIAB INTEGER ::= 1024
maxnoofMappingEntries INTEGER ::= 67108864
maxnoofDSInfo INTEGER ::= 64
maxnoofEgressLinks INTEGER ::= 2
maxnoofULUPTNLInformationforIAB INTEGER ::= 32678
maxnoofUPTNLAddresses INTEGER ::= 8
maxnoofSLDRBs INTEGER ::= 512
maxnoofQoSParaSets INTEGER ::= 8
maxnoofPC5QoSFlows INTEGER ::= 2048
maxnoofSSBAreas INTEGER ::= 64
maxnoofPhysicalResourceBlocks INTEGER ::= 275
maxnoofPhysicalResourceBlocks-1 INTEGER ::= 274
maxnoofPRACHconfigs INTEGER ::= 16
maxnoofRACHReports INTEGER ::= 64
maxnoofRLFReports INTEGER ::= 64
maxnoofAdditionalPDCPDuplicationTNL INTEGER ::= 2
maxnoofRLCDuplicationState INTEGER ::= 3
maxnoofCHOcells INTEGER ::= 8
maxnoofMDTPLMNs INTEGER ::= 16
maxnoofCAGsupported INTEGER ::= 12
maxnoofNIDsupported INTEGER ::= 12
maxnoofNRSCSs INTEGER ::= 5
maxnoofExtSliceItems INTEGER ::= 65535
maxnoofPosMeas INTEGER ::= 16384
maxnoofTRPInfoTypes INTEGER ::= 64
maxnoofTRPs INTEGER ::= 65535
maxnoofSRSTriggerStates INTEGER ::= 3
maxnoofSpatialRelations INTEGER ::= 64
maxnoBcastCell INTEGER ::= 16384
maxnoofAngleInfo INTEGER ::= 65535
maxnooflcs-gcs-translation INTEGER ::= 3
maxnoofPath INTEGER ::= 2
maxnoofMeasE-CID INTEGER ::= 64
maxnoofSSBs INTEGER ::= 255
maxnoSRS-ResourceSets INTEGER ::= 16
maxnoSRS-ResourcePerSet INTEGER ::= 16
maxnoSRS-Carriers INTEGER ::= 32
maxnoSCSs INTEGER ::= 5
maxnoSRS-Resources INTEGER ::= 64
maxnoSRS-PosResources INTEGER ::= 64
maxnoSRS-PosResourceSets INTEGER ::= 16
maxnoSRS-PosResourcePerSet INTEGER ::= 16
maxnoofPRS-ResourceSets INTEGER ::= 2
maxnoofPRS-ResourcesPerSet INTEGER ::= 64
maxNoOfMeasTRPs INTEGER ::= 64
maxnoofPRSresourceSets INTEGER ::= 8
maxnoofPRSresources INTEGER ::= 64

-- **************************************************************
--
-- IEs
--
-- **************************************************************

id-Cause ProtocolIE-ID ::= 0
id-Cells-Failed-to-be-Activated-List ProtocolIE-ID ::= 1
id-Cells-Failed-to-be-Activated-List-Item ProtocolIE-ID ::= 2
id-Cells-to-be-Activated-List ProtocolIE-ID ::= 3
id-Cells-to-be-Activated-List-Item ProtocolIE-ID ::= 4
id-Cells-to-be-Deactivated-List ProtocolIE-ID ::= 5
id-Cells-to-be-Deactivated-List-Item ProtocolIE-ID ::= 6
id-CriticalityDiagnostics ProtocolIE-ID ::= 7
id-CUtoDURRCInformation ProtocolIE-ID ::= 9
id-DRBs-FailedToBeModified-Item ProtocolIE-ID ::= 12
id-DRBs-FailedToBeModified-List ProtocolIE-ID ::= 13
id-DRBs-FailedToBeSetup-Item ProtocolIE-ID ::= 14
id-DRBs-FailedToBeSetup-List ProtocolIE-ID ::= 15
id-DRBs-FailedToBeSetupMod-Item ProtocolIE-ID ::= 16
id-DRBs-FailedToBeSetupMod-List ProtocolIE-ID ::= 17
id-DRBs-ModifiedConf-Item ProtocolIE-ID ::= 18
id-DRBs-ModifiedConf-List ProtocolIE-ID ::= 19
id-DRBs-Modified-Item ProtocolIE-ID ::= 20
id-DRBs-Modified-List ProtocolIE-ID ::= 21
id-DRBs-Required-ToBeModified-Item ProtocolIE-ID ::= 22
id-DRBs-Required-ToBeModified-List ProtocolIE-ID ::= 23
id-DRBs-Required-ToBeReleased-Item ProtocolIE-ID ::= 24
id-DRBs-Required-ToBeReleased-List ProtocolIE-ID ::= 25
id-DRBs-Setup-Item ProtocolIE-ID ::= 26
id-DRBs-Setup-List ProtocolIE-ID ::= 27
id-DRBs-SetupMod-Item ProtocolIE-ID ::= 28
id-DRBs-SetupMod-List ProtocolIE-ID ::= 29
id-DRBs-ToBeModified-Item ProtocolIE-ID ::= 30
id-DRBs-ToBeModified-List ProtocolIE-ID ::= 31
id-DRBs-ToBeReleased-Item ProtocolIE-ID ::= 32
id-DRBs-ToBeReleased-List ProtocolIE-ID ::= 33
id-DRBs-ToBeSetup-Item ProtocolIE-ID ::= 34
id-DRBs-ToBeSetup-List ProtocolIE-ID ::= 35
id-DRBs-ToBeSetupMod-Item ProtocolIE-ID ::= 36
id-DRBs-ToBeSetupMod-List ProtocolIE-ID ::= 37
id-DRXCycle ProtocolIE-ID ::= 38
id-DUtoCURRCInformation ProtocolIE-ID ::= 39
id-gNB-CU-UE-F1AP-ID ProtocolIE-ID ::= 40
id-gNB-DU-UE-F1AP-ID ProtocolIE-ID ::= 41
id-gNB-DU-ID ProtocolIE-ID ::= 42
id-GNB-DU-Served-Cells-Item ProtocolIE-ID ::= 43
id-gNB-DU-Served-Cells-List ProtocolIE-ID ::= 44
id-gNB-DU-Name ProtocolIE-ID ::= 45
id-NRCellID ProtocolIE-ID ::= 46
id-oldgNB-DU-UE-F1AP-ID ProtocolIE-ID ::= 47
id-ResetType ProtocolIE-ID ::= 48
id-ResourceCoordinationTransferContainer ProtocolIE-ID ::= 49
id-RRCContainer ProtocolIE-ID ::= 50
id-SCell-ToBeRemoved-Item ProtocolIE-ID ::= 51
id-SCell-ToBeRemoved-List ProtocolIE-ID ::= 52
id-SCell-ToBeSetup-Item ProtocolIE-ID ::= 53
id-SCell-ToBeSetup-List ProtocolIE-ID ::= 54
id-SCell-ToBeSetupMod-Item ProtocolIE-ID ::= 55
id-SCell-ToBeSetupMod-List ProtocolIE-ID ::= 56
id-Served-Cells-To-Add-Item ProtocolIE-ID ::= 57
id-Served-Cells-To-Add-List ProtocolIE-ID ::= 58
id-Served-Cells-To-Delete-Item ProtocolIE-ID ::= 59
id-Served-Cells-To-Delete-List ProtocolIE-ID ::= 60
id-Served-Cells-To-Modify-Item ProtocolIE-ID ::= 61
id-Served-Cells-To-Modify-List ProtocolIE-ID ::= 62
id-SpCell-ID ProtocolIE-ID ::= 63
id-SRBID ProtocolIE-ID ::= 64
id-SRBs-FailedToBeSetup-Item ProtocolIE-ID ::= 65
id-SRBs-FailedToBeSetup-List ProtocolIE-ID ::= 66
id-SRBs-FailedToBeSetupMod-Item ProtocolIE-ID ::= 67
id-SRBs-FailedToBeSetupMod-List ProtocolIE-ID ::= 68
id-SRBs-Required-ToBeReleased-Item ProtocolIE-ID ::= 69
id-SRBs-Required-ToBeReleased-List ProtocolIE-ID ::= 70
id-SRBs-ToBeReleased-Item ProtocolIE-ID ::= 71
id-SRBs-ToBeReleased-List ProtocolIE-ID ::= 72
id-SRBs-ToBeSetup-Item ProtocolIE-ID ::= 73
id-SRBs-ToBeSetup-List ProtocolIE-ID ::= 74
id-SRBs-ToBeSetupMod-Item ProtocolIE-ID ::= 75
id-SRBs-ToBeSetupMod-List ProtocolIE-ID ::= 76
id-TimeToWait ProtocolIE-ID ::= 77
id-TransactionID ProtocolIE-ID ::= 78
id-TransmissionActionIndicator ProtocolIE-ID ::= 79
id-UE-associatedLogicalF1-ConnectionItem ProtocolIE-ID ::= 80
id-UE-associatedLogicalF1-ConnectionListResAck ProtocolIE-ID ::= 81
id-gNB-CU-Name ProtocolIE-ID ::= 82
id-SCell-FailedtoSetup-List ProtocolIE-ID ::= 83
id-SCell-FailedtoSetup-Item ProtocolIE-ID ::= 84
id-SCell-FailedtoSetupMod-List ProtocolIE-ID ::= 85
id-SCell-FailedtoSetupMod-Item ProtocolIE-ID ::= 86
id-RRCReconfigurationCompleteIndicator ProtocolIE-ID ::= 87
id-Cells-Status-Item ProtocolIE-ID ::= 88
id-Cells-Status-List ProtocolIE-ID ::= 89
id-Candidate-SpCell-List ProtocolIE-ID ::= 90
id-Candidate-SpCell-Item ProtocolIE-ID ::= 91
id-Potential-SpCell-List ProtocolIE-ID ::= 92
id-Potential-SpCell-Item ProtocolIE-ID ::= 93
id-FullConfiguration ProtocolIE-ID ::= 94
id-C-RNTI ProtocolIE-ID ::= 95
id-SpCellULConfigured ProtocolIE-ID ::= 96
id-InactivityMonitoringRequest ProtocolIE-ID ::= 97
id-InactivityMonitoringResponse ProtocolIE-ID ::= 98
id-DRB-Activity-Item ProtocolIE-ID ::= 99
id-DRB-Activity-List ProtocolIE-ID ::= 100
id-EUTRA-NR-CellResourceCoordinationReq-Container ProtocolIE-ID ::= 101
id-EUTRA-NR-CellResourceCoordinationReqAck-Container ProtocolIE-ID ::= 102
id-Protected-EUTRA-Resources-List ProtocolIE-ID ::= 105
id-RequestType ProtocolIE-ID ::= 106
id-ServCellIndex ProtocolIE-ID ::= 107
id-RAT-FrequencyPriorityInformation ProtocolIE-ID ::= 108
id-ExecuteDuplication ProtocolIE-ID ::= 109
id-NRCGI ProtocolIE-ID ::= 111
id-PagingCell-Item ProtocolIE-ID ::= 112
id-PagingCell-List ProtocolIE-ID ::= 113
id-PagingDRX ProtocolIE-ID ::= 114
id-PagingPriority ProtocolIE-ID ::= 115
id-SItype-List ProtocolIE-ID ::= 116
id-UEIdentityIndexValue ProtocolIE-ID ::= 117
id-gNB-CUSystemInformation ProtocolIE-ID ::= 118
id-HandoverPreparationInformation ProtocolIE-ID ::= 119
id-GNB-CU-TNL-Association-To-Add-Item ProtocolIE-ID ::= 120
id-GNB-CU-TNL-Association-To-Add-List ProtocolIE-ID ::= 121
id-GNB-CU-TNL-Association-To-Remove-Item ProtocolIE-ID ::= 122
id-GNB-CU-TNL-Association-To-Remove-List ProtocolIE-ID ::= 123
id-GNB-CU-TNL-Association-To-Update-Item ProtocolIE-ID ::= 124
id-GNB-CU-TNL-Association-To-Update-List ProtocolIE-ID ::= 125
id-MaskedIMEISV ProtocolIE-ID ::= 126
id-PagingIdentity ProtocolIE-ID ::= 127
id-DUtoCURRCContainer ProtocolIE-ID ::= 128
id-Cells-to-be-Barred-List ProtocolIE-ID ::= 129
id-Cells-to-be-Barred-Item ProtocolIE-ID ::= 130
id-TAISliceSupportList ProtocolIE-ID ::= 131
id-GNB-CU-TNL-Association-Setup-List ProtocolIE-ID ::= 132
id-GNB-CU-TNL-Association-Setup-Item ProtocolIE-ID ::= 133
id-GNB-CU-TNL-Association-Failed-To-Setup-List ProtocolIE-ID ::= 134
id-GNB-CU-TNL-Association-Failed-To-Setup-Item ProtocolIE-ID ::= 135
id-DRB-Notify-Item ProtocolIE-ID ::= 136
id-DRB-Notify-List ProtocolIE-ID ::= 137
id-NotficationControl ProtocolIE-ID ::= 138
id-RANAC ProtocolIE-ID ::= 139
id-PWSSystemInformation ProtocolIE-ID ::= 140
id-RepetitionPeriod ProtocolIE-ID ::= 141
id-NumberofBroadcastRequest ProtocolIE-ID ::= 142
id-Cells-To-Be-Broadcast-List ProtocolIE-ID ::= 144
id-Cells-To-Be-Broadcast-Item ProtocolIE-ID ::= 145
id-Cells-Broadcast-Completed-List ProtocolIE-ID ::= 146
id-Cells-Broadcast-Completed-Item ProtocolIE-ID ::= 147
id-Broadcast-To-Be-Cancelled-List ProtocolIE-ID ::= 148
id-Broadcast-To-Be-Cancelled-Item ProtocolIE-ID ::= 149
id-Cells-Broadcast-Cancelled-List ProtocolIE-ID ::= 150
id-Cells-Broadcast-Cancelled-Item ProtocolIE-ID ::= 151
id-NR-CGI-List-For-Restart-List ProtocolIE-ID ::= 152
id-NR-CGI-List-For-Restart-Item ProtocolIE-ID ::= 153
id-PWS-Failed-NR-CGI-List ProtocolIE-ID ::= 154
id-PWS-Failed-NR-CGI-Item ProtocolIE-ID ::= 155
id-ConfirmedUEID ProtocolIE-ID ::= 156
id-Cancel-all-Warning-Messages-Indicator ProtocolIE-ID ::= 157
id-GNB-DU-UE-AMBR-UL ProtocolIE-ID ::= 158
id-DRXConfigurationIndicator ProtocolIE-ID ::= 159
id-RLC-Status ProtocolIE-ID ::= 160
id-DLPDCPSNLength ProtocolIE-ID ::= 161
id-GNB-DUConfigurationQuery ProtocolIE-ID ::= 162
id-MeasurementTimingConfiguration ProtocolIE-ID ::= 163
id-DRB-Information ProtocolIE-ID ::= 164
id-ServingPLMN ProtocolIE-ID ::= 165
id-Protected-EUTRA-Resources-Item ProtocolIE-ID ::= 168
id-GNB-CU-RRC-Version ProtocolIE-ID ::= 170
id-GNB-DU-RRC-Version ProtocolIE-ID ::= 171
id-GNBDUOverloadInformation ProtocolIE-ID ::= 172
id-CellGroupConfig ProtocolIE-ID ::= 173
id-RLCFailureIndication ProtocolIE-ID ::= 174
id-UplinkTxDirectCurrentListInformation ProtocolIE-ID ::= 175
id-DC-Based-Duplication-Configured ProtocolIE-ID ::= 176
id-DC-Based-Duplication-Activation ProtocolIE-ID ::= 177
id-SULAccessIndication ProtocolIE-ID ::= 178
id-AvailablePLMNList ProtocolIE-ID ::= 179
id-PDUSessionID ProtocolIE-ID ::= 180
id-ULPDUSessionAggregateMaximumBitRate ProtocolIE-ID ::= 181
id-ServingCellMO ProtocolIE-ID ::= 182
id-QoSFlowMappingIndication ProtocolIE-ID ::= 183
id-RRCDeliveryStatusRequest ProtocolIE-ID ::= 184
id-RRCDeliveryStatus ProtocolIE-ID ::= 185
id-BearerTypeChange ProtocolIE-ID ::= 186
id-RLCMode ProtocolIE-ID ::= 187
id-Duplication-Activation ProtocolIE-ID ::= 188
id-Dedicated-SIDelivery-NeededUE-List ProtocolIE-ID ::= 189
id-Dedicated-SIDelivery-NeededUE-Item ProtocolIE-ID ::= 190
id-DRX-LongCycleStartOffset ProtocolIE-ID ::= 191
id-ULPDCPSNLength ProtocolIE-ID ::= 192
id-SelectedBandCombinationIndex ProtocolIE-ID ::= 193
id-SelectedFeatureSetEntryIndex ProtocolIE-ID ::= 194
id-ResourceCoordinationTransferInformation ProtocolIE-ID ::= 195
id-ExtendedServedPLMNs-List ProtocolIE-ID ::= 196
id-ExtendedAvailablePLMN-List ProtocolIE-ID ::= 197
id-Associated-SCell-List ProtocolIE-ID ::= 198
id-latest-RRC-Version-Enhanced ProtocolIE-ID ::= 199
id-Associated-SCell-Item ProtocolIE-ID ::= 200
id-Cell-Direction ProtocolIE-ID ::= 201
id-SRBs-Setup-List ProtocolIE-ID ::= 202
id-SRBs-Setup-Item ProtocolIE-ID ::= 203
id-SRBs-SetupMod-List ProtocolIE-ID ::= 204
id-SRBs-SetupMod-Item ProtocolIE-ID ::= 205
id-SRBs-Modified-List ProtocolIE-ID ::= 206
id-SRBs-Modified-Item ProtocolIE-ID ::= 207
id-Ph-InfoSCG ProtocolIE-ID ::= 208
id-RequestedBandCombinationIndex ProtocolIE-ID ::= 209
id-RequestedFeatureSetEntryIndex ProtocolIE-ID ::= 210
id-RequestedP-MaxFR2 ProtocolIE-ID ::= 211
id-DRX-Config ProtocolIE-ID ::= 212
id-IgnoreResourceCoordinationContainer ProtocolIE-ID ::= 213
id-UEAssistanceInformation ProtocolIE-ID ::= 214
id-NeedforGap ProtocolIE-ID ::= 215
id-PagingOrigin ProtocolIE-ID ::= 216
id-new-gNB-CU-UE-F1AP-ID ProtocolIE-ID ::= 217
id-RedirectedRRCmessage ProtocolIE-ID ::= 218
id-new-gNB-DU-UE-F1AP-ID ProtocolIE-ID ::= 219
id-NotificationInformation ProtocolIE-ID ::= 220
id-PLMNAssistanceInfoForNetShar ProtocolIE-ID ::= 221
id-UEContextNotRetrievable ProtocolIE-ID ::= 222
id-BPLMN-ID-Info-List ProtocolIE-ID ::= 223
id-SelectedPLMNID ProtocolIE-ID ::= 224
id-UAC-Assistance-Info ProtocolIE-ID ::= 225
id-RANUEID ProtocolIE-ID ::= 226
id-GNB-DU-TNL-Association-To-Remove-Item ProtocolIE-ID ::= 227
id-GNB-DU-TNL-Association-To-Remove-List ProtocolIE-ID ::= 228
id-TNLAssociationTransportLayerAddressgNBDU ProtocolIE-ID ::= 229
id-portNumber ProtocolIE-ID ::= 230
id-AdditionalSIBMessageList ProtocolIE-ID ::= 231
id-Cell-Type ProtocolIE-ID ::= 232
id-IgnorePRACHConfiguration ProtocolIE-ID ::= 233
id-CG-Config ProtocolIE-ID ::= 234
id-PDCCH-BlindDetectionSCG ProtocolIE-ID ::= 235
id-Requested-PDCCH-BlindDetectionSCG ProtocolIE-ID ::= 236
id-Ph-InfoMCG ProtocolIE-ID ::= 237
id-MeasGapSharingConfig ProtocolIE-ID ::= 238
id-systemInformationAreaID ProtocolIE-ID ::= 239
id-areaScope ProtocolIE-ID ::= 240
id-RRCContainer-RRCSetupComplete ProtocolIE-ID ::= 241
id-TraceActivation ProtocolIE-ID ::= 242
id-TraceID ProtocolIE-ID ::= 243
id-Neighbour-Cell-Information-List ProtocolIE-ID ::= 244
id-SymbolAllocInSlot ProtocolIE-ID ::= 246
id-NumDLULSymbols ProtocolIE-ID ::= 247
id-AdditionalRRMPriorityIndex ProtocolIE-ID ::= 248
id-DUCURadioInformationType ProtocolIE-ID ::= 249
id-CUDURadioInformationType ProtocolIE-ID ::= 250
id-AggressorgNBSetID ProtocolIE-ID ::= 251
id-VictimgNBSetID ProtocolIE-ID ::= 252
id-LowerLayerPresenceStatusChange ProtocolIE-ID ::= 253
id-Transport-Layer-Address-Info ProtocolIE-ID ::= 254
id-Neighbour-Cell-Information-Item ProtocolIE-ID ::= 255
id-IntendedTDD-DL-ULConfig ProtocolIE-ID ::= 256
id-QosMonitoringRequest ProtocolIE-ID ::= 257
id-BHChannels-ToBeSetup-List ProtocolIE-ID ::= 258
id-BHChannels-ToBeSetup-Item ProtocolIE-ID ::= 259
id-BHChannels-Setup-List ProtocolIE-ID ::= 260
id-BHChannels-Setup-Item ProtocolIE-ID ::= 261
id-BHChannels-ToBeModified-Item ProtocolIE-ID ::= 262
id-BHChannels-ToBeModified-List ProtocolIE-ID ::= 263
id-BHChannels-ToBeReleased-Item ProtocolIE-ID ::= 264
id-BHChannels-ToBeReleased-List ProtocolIE-ID ::= 265
id-BHChannels-ToBeSetupMod-Item ProtocolIE-ID ::= 266
id-BHChannels-ToBeSetupMod-List ProtocolIE-ID ::= 267
id-BHChannels-FailedToBeModified-Item ProtocolIE-ID ::= 268
id-BHChannels-FailedToBeModified-List ProtocolIE-ID ::= 269
id-BHChannels-FailedToBeSetupMod-Item ProtocolIE-ID ::= 270
id-BHChannels-FailedToBeSetupMod-List ProtocolIE-ID ::= 271
id-BHChannels-Modified-Item ProtocolIE-ID ::= 272
id-BHChannels-Modified-List ProtocolIE-ID ::= 273
id-BHChannels-SetupMod-Item ProtocolIE-ID ::= 274
id-BHChannels-SetupMod-List ProtocolIE-ID ::= 275
id-BHChannels-Required-ToBeReleased-Item ProtocolIE-ID ::= 276
id-BHChannels-Required-ToBeReleased-List ProtocolIE-ID ::= 277
id-BHChannels-FailedToBeSetup-Item ProtocolIE-ID ::= 278
id-BHChannels-FailedToBeSetup-List ProtocolIE-ID ::= 279
id-BHInfo ProtocolIE-ID ::= 280
id-BAPAddress ProtocolIE-ID ::= 281
id-ConfiguredBAPAddress ProtocolIE-ID ::= 282
id-BH-Routing-Information-Added-List ProtocolIE-ID ::= 283
id-BH-Routing-Information-Added-List-Item ProtocolIE-ID ::= 284
id-BH-Routing-Information-Removed-List ProtocolIE-ID ::= 285
id-BH-Routing-Information-Removed-List-Item ProtocolIE-ID ::= 286
id-UL-BH-Non-UP-Traffic-Mapping ProtocolIE-ID ::= 287
id-Activated-Cells-to-be-Updated-List ProtocolIE-ID ::= 288
id-Child-Nodes-List ProtocolIE-ID ::= 289
id-IAB-Info-IAB-DU ProtocolIE-ID ::= 290
id-IAB-Info-IAB-donor-CU ProtocolIE-ID ::= 291
id-IAB-TNL-Addresses-To-Remove-List ProtocolIE-ID ::= 292
id-IAB-TNL-Addresses-To-Remove-Item ProtocolIE-ID ::= 293
id-IAB-Allocated-TNL-Address-List ProtocolIE-ID ::= 294
id-IAB-Allocated-TNL-Address-Item ProtocolIE-ID ::= 295
id-IABIPv6RequestType ProtocolIE-ID ::= 296
id-IABv4AddressesRequested ProtocolIE-ID ::= 297
id-IAB-Barred ProtocolIE-ID ::= 298
id-TrafficMappingInformation ProtocolIE-ID ::= 299
id-UL-UP-TNL-Information-to-Update-List ProtocolIE-ID ::= 300
id-UL-UP-TNL-Information-to-Update-List-Item ProtocolIE-ID ::= 301
id-UL-UP-TNL-Address-to-Update-List ProtocolIE-ID ::= 302
id-UL-UP-TNL-Address-to-Update-List-Item ProtocolIE-ID ::= 303
id-DL-UP-TNL-Address-to-Update-List ProtocolIE-ID ::= 304
id-DL-UP-TNL-Address-to-Update-List-Item ProtocolIE-ID ::= 305
id-NRV2XServicesAuthorized ProtocolIE-ID ::= 306
id-LTEV2XServicesAuthorized ProtocolIE-ID ::= 307
id-NRUESidelinkAggregateMaximumBitrate ProtocolIE-ID ::= 308
id-LTEUESidelinkAggregateMaximumBitrate ProtocolIE-ID ::= 309
id-SIB12-message ProtocolIE-ID ::= 310
id-SIB13-message ProtocolIE-ID ::= 311
id-SIB14-message ProtocolIE-ID ::= 312
id-SLDRBs-FailedToBeModified-Item ProtocolIE-ID ::= 313
id-SLDRBs-FailedToBeModified-List ProtocolIE-ID ::= 314
id-SLDRBs-FailedToBeSetup-Item ProtocolIE-ID ::= 315
id-SLDRBs-FailedToBeSetup-List ProtocolIE-ID ::= 316
id-SLDRBs-Modified-Item ProtocolIE-ID ::= 317
id-SLDRBs-Modified-List ProtocolIE-ID ::= 318
id-SLDRBs-Required-ToBeModified-Item ProtocolIE-ID ::= 319
id-SLDRBs-Required-ToBeModified-List ProtocolIE-ID ::= 320
id-SLDRBs-Required-ToBeReleased-Item ProtocolIE-ID ::= 321
id-SLDRBs-Required-ToBeReleased-List ProtocolIE-ID ::= 322
id-SLDRBs-Setup-Item ProtocolIE-ID ::= 323
id-SLDRBs-Setup-List ProtocolIE-ID ::= 324
id-SLDRBs-ToBeModified-Item ProtocolIE-ID ::= 325
id-SLDRBs-ToBeModified-List ProtocolIE-ID ::= 326
id-SLDRBs-ToBeReleased-Item ProtocolIE-ID ::= 327
id-SLDRBs-ToBeReleased-List ProtocolIE-ID ::= 328
id-SLDRBs-ToBeSetup-Item ProtocolIE-ID ::= 329
id-SLDRBs-ToBeSetup-List ProtocolIE-ID ::= 330
id-SLDRBs-ToBeSetupMod-Item ProtocolIE-ID ::= 331
id-SLDRBs-ToBeSetupMod-List ProtocolIE-ID ::= 332
id-SLDRBs-SetupMod-List ProtocolIE-ID ::= 333
id-SLDRBs-FailedToBeSetupMod-List ProtocolIE-ID ::= 334
id-SLDRBs-SetupMod-Item ProtocolIE-ID ::= 335
id-SLDRBs-FailedToBeSetupMod-Item ProtocolIE-ID ::= 336
id-SLDRBs-ModifiedConf-List ProtocolIE-ID ::= 337
id-SLDRBs-ModifiedConf-Item ProtocolIE-ID ::= 338
id-UEAssistanceInformationEUTRA ProtocolIE-ID ::= 339
id-PC5LinkAMBR ProtocolIE-ID ::= 340
id-SL-PHY-MAC-RLC-Config ProtocolIE-ID ::= 341
id-SL-ConfigDedicatedEUTRA-Info ProtocolIE-ID ::= 342
id-AlternativeQoSParaSetList ProtocolIE-ID ::= 343
id-CurrentQoSParaSetIndex ProtocolIE-ID ::= 344
id-gNBCUMeasurementID ProtocolIE-ID ::= 345
id-gNBDUMeasurementID ProtocolIE-ID ::= 346
id-RegistrationRequest ProtocolIE-ID ::= 347
id-ReportCharacteristics ProtocolIE-ID ::= 348
id-CellToReportList ProtocolIE-ID ::= 349
id-CellMeasurementResultList ProtocolIE-ID ::= 350
id-HardwareLoadIndicator ProtocolIE-ID ::= 351
id-ReportingPeriodicity ProtocolIE-ID ::= 352
id-TNLCapacityIndicator ProtocolIE-ID ::= 353
id-CarrierList ProtocolIE-ID ::= 354
id-ULCarrierList ProtocolIE-ID ::= 355
id-FrequencyShift7p5khz ProtocolIE-ID ::= 356
id-SSB-PositionsInBurst ProtocolIE-ID ::= 357
id-NRPRACHConfig ProtocolIE-ID ::= 358
id-RACHReportInformationList ProtocolIE-ID ::= 359
id-RLFReportInformationList ProtocolIE-ID ::= 360
id-TDD-UL-DLConfigCommonNR ProtocolIE-ID ::= 361
id-CNPacketDelayBudgetDownlink ProtocolIE-ID ::= 362
id-ExtendedPacketDelayBudget ProtocolIE-ID ::= 363
id-TSCTrafficCharacteristics ProtocolIE-ID ::= 364
id-ReportingRequestType ProtocolIE-ID ::= 365
id-TimeReferenceInformation ProtocolIE-ID ::= 366
id-CNPacketDelayBudgetUplink ProtocolIE-ID ::= 369
id-AdditionalPDCPDuplicationTNL-List ProtocolIE-ID ::= 370
id-RLCDuplicationInformation ProtocolIE-ID ::= 371
id-AdditionalDuplicationIndication ProtocolIE-ID ::= 372
id-ConditionalInterDUMobilityInformation ProtocolIE-ID ::= 373
id-ConditionalIntraDUMobilityInformation ProtocolIE-ID ::= 374
id-targetCellsToCancel ProtocolIE-ID ::= 375
id-requestedTargetCellGlobalID ProtocolIE-ID ::= 376
id-ManagementBasedMDTPLMNList ProtocolIE-ID ::= 377
id-TraceCollectionEntityIPAddress ProtocolIE-ID ::= 378
id-PrivacyIndicator ProtocolIE-ID ::= 379
id-TraceCollectionEntityURI ProtocolIE-ID ::= 380
id-mdtConfiguration ProtocolIE-ID ::= 381
id-ServingNID ProtocolIE-ID ::= 382
id-NPNBroadcastInformation ProtocolIE-ID ::= 383
id-NPNSupportInfo ProtocolIE-ID ::= 384
id-NID ProtocolIE-ID ::= 385
id-AvailableSNPN-ID-List ProtocolIE-ID ::= 386
id-SIB10-message ProtocolIE-ID ::= 387
id-DLCarrierList ProtocolIE-ID ::= 389
id-ExtendedTAISliceSupportList ProtocolIE-ID ::= 390
id-RequestedSRSTransmissionCharacteristics ProtocolIE-ID ::= 391
id-PosAssistance-Information ProtocolIE-ID ::= 392
id-PosBroadcast ProtocolIE-ID ::= 393
id-RoutingID ProtocolIE-ID ::= 394
id-PosAssistanceInformationFailureList ProtocolIE-ID ::= 395
id-PosMeasurementQuantities ProtocolIE-ID ::= 396
id-PosMeasurementResultList ProtocolIE-ID ::= 397
id-TRPInformationTypeListTRPReq ProtocolIE-ID ::= 398
id-TRPInformationTypeItem ProtocolIE-ID ::= 399
id-TRPInformationListTRPResp ProtocolIE-ID ::= 400
id-TRPInformationItem ProtocolIE-ID ::= 401
id-LMF-MeasurementID ProtocolIE-ID ::= 402
id-SRSType ProtocolIE-ID ::= 403
id-ActivationTime ProtocolIE-ID ::= 404
id-AbortTransmission ProtocolIE-ID ::= 405
id-PositioningBroadcastCells ProtocolIE-ID ::= 406
id-SRSConfiguration ProtocolIE-ID ::= 407
id-PosReportCharacteristics ProtocolIE-ID ::= 408
id-PosMeasurementPeriodicity ProtocolIE-ID ::= 409
id-TRPList ProtocolIE-ID ::= 410
id-RAN-MeasurementID ProtocolIE-ID ::= 411
id-LMF-UE-MeasurementID ProtocolIE-ID ::= 412
id-RAN-UE-MeasurementID ProtocolIE-ID ::= 413
id-E-CID-MeasurementQuantities ProtocolIE-ID ::= 414
id-E-CID-MeasurementQuantities-Item ProtocolIE-ID ::= 415
id-E-CID-MeasurementPeriodicity ProtocolIE-ID ::= 416
id-E-CID-MeasurementResult ProtocolIE-ID ::= 417
id-Cell-Portion-ID ProtocolIE-ID ::= 418
id-SFNInitialisationTime ProtocolIE-ID ::= 419
id-SystemFrameNumber ProtocolIE-ID ::= 420
id-SlotNumber ProtocolIE-ID ::= 421
id-TRP-MeasurementRequestList ProtocolIE-ID ::= 422
id-MeasurementBeamInfoRequest ProtocolIE-ID ::= 423
id-E-CID-ReportCharacteristics ProtocolIE-ID ::= 424
id-ConfiguredTACIndication ProtocolIE-ID ::= 425
id-Extended-GNB-CU-Name ProtocolIE-ID ::= 426
id-Extended-GNB-DU-Name ProtocolIE-ID ::= 427
id-F1CTransferPath ProtocolIE-ID ::= 428
id-SFN-Offset ProtocolIE-ID ::= 429
id-TransmissionStopIndicator ProtocolIE-ID ::= 430
id-SrsFrequency ProtocolIE-ID ::= 431
id-SCGIndicator ProtocolIE-ID ::= 432
id-EstimatedArrivalProbability ProtocolIE-ID ::= 433
id-TRPType ProtocolIE-ID ::= 434
id-SRSSpatialRelationPerSRSResource ProtocolIE-ID ::= 435

END
-- ASN1STOP

-- ASN1START
-- **************************************************************
--
-- Container definitions
--
-- **************************************************************

F1AP-Containers {
   itu-t (0) identified-organization (4) etsi (0) mobileDomain (0)
ngran-access (22) modules (3) f1ap (3) version1 (1) f1ap-Containers (5) }

DEFINITIONS AUTOMATIC TAGS ::=

BEGIN

-- **************************************************************
--
-- IE parameter types from other modules.
--
-- **************************************************************

IMPORTS
Criticality,
Presence,
PrivateIE-ID,
ProtocolExtensionID,
ProtocolIE-ID

FROM F1AP-CommonDataTypes
maxPrivateIEs,
maxProtocolExtensions,
maxProtocolIEs

FROM F1AP-Constants;

-- **************************************************************
--
-- Class Definition for Protocol IEs
--
-- **************************************************************

F1AP-PROTOCOL-IES ::= CLASS {
   &id ProtocolIE-ID UNIQUE,
   &criticality Criticality,
   &Value,
   &presence Presence
}
WITH SYNTAX {
   ID &id
   CRITICALITY &criticality
   TYPE &Value
   PRESENCE &presence
}

-- **************************************************************
--
-- Class Definition for Protocol IEs
--
-- **************************************************************

F1AP-PROTOCOL-IES-PAIR ::= CLASS {
   &id ProtocolIE-ID UNIQUE,
   &firstCriticality Criticality,
   &FirstValue,
   &secondCriticality Criticality,
   &SecondValue,
   &presence Presence
}
WITH SYNTAX {
   ID &id
   FIRST CRITICALITY &firstCriticality
   FIRST TYPE &FirstValue
   SECOND CRITICALITY &secondCriticality
   SECOND TYPE &SecondValue
   PRESENCE &presence
}

-- **************************************************************
--
-- Class Definition for Protocol Extensions
--
-- **************************************************************

F1AP-PROTOCOL-EXTENSION ::= CLASS {
   &id ProtocolExtensionID UNIQUE,
   &criticality Criticality,
   &Extension,
   &presence Presence
}
WITH SYNTAX {
   ID &id
   CRITICALITY &criticality
   EXTENSION &Extension
   PRESENCE &presence
}

-- **************************************************************
--
-- Class Definition for Private IEs
--
-- **************************************************************

F1AP-PRIVATE-IES ::= CLASS {
   &id PrivateIE-ID,
   &criticality Criticality,
   &Value,
   &presence Presence
}
WITH SYNTAX {
   ID &id
   CRITICALITY &criticality
   TYPE &Value
   PRESENCE &presence
}

-- **************************************************************
--
-- Container for Protocol IEs
--
-- **************************************************************

ProtocolIE-Container {F1AP-PROTOCOL-IES : IEsSetParam} ::=
SEQUENCE (SIZE (0..maxProtocolIEs)) OF
ProtocolIE-Field {{IEsSetParam}}

ProtocolIE-SingleContainer {F1AP-PROTOCOL-IES : IEsSetParam} ::=
ProtocolIE-Field {{IEsSetParam}}

ProtocolIE-Field {F1AP-PROTOCOL-IES : IEsSetParam} ::= SEQUENCE {
   id F1AP-PROTOCOL-IES.&id ({IEsSetParam}),
   criticality F1AP-PROTOCOL-IES.&criticality ({IEsSetParam}{@id}),
   value F1AP-PROTOCOL-IES.&Value ({IEsSetParam}{@id})
}

-- **************************************************************
--
-- Container for Protocol IE Pairs
--
-- **************************************************************

ProtocolIE-ContainerPair {F1AP-PROTOCOL-IES-PAIR : IEsSetParam} ::=
SEQUENCE (SIZE (0..maxProtocolIEs)) OF
ProtocolIE-FieldPair {{IEsSetParam}}

ProtocolIE-FieldPair {F1AP-PROTOCOL-IES-PAIR : IEsSetParam} ::= SEQUENCE {
   id F1AP-PROTOCOL-IES-PAIR.&id ({IEsSetParam}),
   firstCriticality F1AP-PROTOCOL-IES-PAIR.&firstCriticality ({IEsSetParam}{@id}),
   firstValue F1AP-PROTOCOL-IES-PAIR.&FirstValue ({IEsSetParam}{@id}),
   secondCriticality F1AP-PROTOCOL-IES-PAIR.&secondCriticality ({IEsSetParam}{@id}),
   secondValue F1AP-PROTOCOL-IES-PAIR.&SecondValue ({IEsSetParam}{@id})
}

-- **************************************************************
--
-- Container for Protocol Extensions
--
-- **************************************************************

ProtocolExtensionContainer {F1AP-PROTOCOL-EXTENSION : ExtensionSetParam} ::=
SEQUENCE (SIZE (1..maxProtocolExtensions)) OF
ProtocolExtensionField {{ExtensionSetParam}}

ProtocolExtensionField {F1AP-PROTOCOL-EXTENSION : ExtensionSetParam} ::= SEQUENCE {
   id F1AP-PROTOCOL-EXTENSION.&id ({ExtensionSetParam}),
   criticality F1AP-PROTOCOL-EXTENSION.&criticality ({ExtensionSetParam}{@id}),
   extensionValue F1AP-PROTOCOL-EXTENSION.&Extension ({ExtensionSetParam}{@id})
}

-- **************************************************************
--
-- Container for Private IEs
--
-- **************************************************************

PrivateIE-Container {F1AP-PRIVATE-IES : IEsSetParam } ::=
SEQUENCE (SIZE (1.. maxPrivateIEs)) OF
PrivateIE-Field {{IEsSetParam}}

PrivateIE-Field {F1AP-PRIVATE-IES : IEsSetParam} ::= SEQUENCE {
   id F1AP-PRIVATE-IES.&id ({IEsSetParam}),
   criticality F1AP-PRIVATE-IES.&criticality ({IEsSetParam}{@id}),
   value F1AP-PRIVATE-IES.&Value ({IEsSetParam}{@id})
}

END
-- ASN1STOP
